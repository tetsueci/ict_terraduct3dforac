(vl-load-com)
;;cpath_terraduct3d
(regapp "attributedata")
(regapp "terraduct3d")
(defun entgettd3(e)(entget e(list "terraduct3d")))
(defun *error*(msg)(princ msg));;保険
(setq bool_viewrotationfirsttime T
      bool_ucsexchangefirsttime T
      prev_select_sessionname ""
      )

(defun c:devtd3d( / e v array_Type array_Data)
  (if(setq e(car(entsel)))
      (progn
        (setq v(vlax-ename->vla-object e))
        (vla-getXData v "terraduct3d" 'array_Type 'array_Data )
        (if array_data(split_list 0(cdr(mapcar 'vlax-variant-value
                                               (vlax-safearray->list array_data)))))))
  )


;;todo;;lineが同一点のときの警告

;;メインコマンド
(defun c:terraduct3d( / func_name dict_dokos bool_guidedisplay array_type array_data)
  (setq x_guidebase 1.)
  (vla-StartUndoMark (vla-get-ActiveDocument (vlax-get-Acad-Object)))
  
  (setq dicts_all(vla-get-Dictionaries(vla-get-ActiveDocument (vlax-get-acad-object))))
  
  (setq str_initialsession "terraduct3d_session_" ls_session(list))
  (vlax-for
   xrec dicts_all
   (if(vl-catch-all-error-p(setq str(vl-catch-all-apply 'vla-get-name (list xrec)))) T
     (if(vl-string-search str_initialsession str)
         (setq ls_session(cons(cons(vl-string-subst "" str_initialsession str)xrec)ls_session))))
   )
  
  (setq ls_session (reverse ls_session))
  
  ;; (mapcar '(lambda(a)(set(read(car a))(cadr a)))ls_dictdata)
  
  (search_sty-lay-blo
   (list(cons "STYLE" 'ls_textstyle)
        (cons "DIMSTYLE" 'ls_dimstyle)
        (cons "LAYER" 'ls_layername)
        ;; (cons "BLOCK" 'ls_blockname)
        ))

  ;; (setq ls_blockname
  ;;       ((lambda(lst / ls0 ls_out ii jj str)
  ;;          (setq ii(ascii(car lst)))
  ;;          (while lst
  ;;            (setq str(car lst)lst(cdr lst)jj(ascii str))
  ;;            (if(= ii jj)(setq ls0(cons str ls0))
  ;;              (setq ls_out(cons(cons ii ls0)ls_out)
  ;;                    ls0(list str)ii jj jj nil)
  ;;              )
  ;;            )
  ;;          (if jj ls_out(cons(cons ii ls0)ls_out)))
  ;;        ls_blockname)
  ;;       ls_blockname(reverse ls_blockname)
  ;;       )
  
  (setq

   cal_viewtopleft
   (lambda(ratio_height
           deltax deltay deltaz bool_3d 
           / height_view ls_screen_size_yx width_view bool_plane)
     (setq p_viewcenter(getvar "VIEWCTR")
           height_view(getvar "VIEWSIZE")
           height_text(* height_view ratio_height)
           vec_view  (if bool_3d(unit_vector(getvar "VIEWDIR"))(list 0 0 1))
           bool_plane(and(<(abs(car vec_view))1e-8)(<(abs(cadr vec_view))1e-8))
           ang_viewtwist(if bool_plane(-(getvar "VIEWTWIST"))0.)
           vec_x_onview(list 1 0 0)vec_y_onview(list 0 1 0)
           )
     (if bool_plane
         (setq vec_x_onview(list(cos ang_viewtwist)(sin ang_viewtwist)0.)
               vec_y_onview(list(-(sin ang_viewtwist))(cos ang_viewtwist)0.) )
       (if bool_3d
           (setq vec_x_onview(trans-x vec_x_onview vec_view(list 0 0 1))
                 vec_y_onview(trans-x vec_y_onview vec_view(list 0 0 1)) )
         ))
     
     (setq ls_screen_size_yx(getvar "SCREENSIZE")
           width_view(/(* height_view(car ls_screen_size_yx))
                       (cadr ls_screen_size_yx))
           deltaz((lambda( / p e v)
                    (if point_guide_center
                        (apply '+(mapcar '(lambda(p1 p2 v)(* v(- p1 p2)))
                                         point_guide_center p_viewcenter vec_view))
                      0.)
                    ))
           
           point_base
           (mapcar '(lambda(p x y z)
                      (+ p
                         (*(+ height_text(* -0.5 deltax width_view))x)
                         (*(+(* deltay height_text)(* 0.5 height_view)) y)
                         (* deltaz z)
                         ))
                   p_viewcenter vec_x_onview vec_y_onview vec_view)
           )
     )

   ;;TYPEがいるのはDCLのとき
   ls_ductparameters;;全角14文字まで
   (list(list(cons "TEXT"(mix_strasc(list 12304 12460 12452 12489 12486 12461 12473 12488 12398 35373 23450 12305)))
             (cons "ITEM" "TEXT"));;ガイドテキストの設定

        (list(cons "SYMBOL" 'str_textstyle_gbo) (cons "INITIALFUNC" (lambda(a)nil))
             (cons "EXPLANE"(mix_strasc(list 25991 23383 12473 12479 12452 12523)))
             )

        (list(cons "TEXT"(mix_strasc(list 25991 23383 12473 12479 12452 12523)))
             (cons "ITEM" "POPUP_LIST")(cons "VALLIST" ls_textstyle);;ガイドテキストの文字スタイル
             (cons "SYMBOL" 'int_textstyle_gbo)(cons "TYPE" "INT")
             (cons "INITIALFUNC" (lambda(a / i)
                                   (if(if str_textstyle_gbo
                                          (setq i(vl-position str_textstyle_gbo ls_textstyle)))T
                                     (if(setq i(vl-position "Standard" ls_textstyle))T
                                       (setq i(vl-position(getvar "TEXTSTYLE")ls_textstyle))))
                                   i))
             (cons "ACTIONLIST"((lambda( / )
                                  (setq action_guidetext
                                        (lambda(str / i)
                                          (setq i(atoi(get_tile str))
                                                int_textstyle_gbo i
                                                str_textstyle_gbo(nth i ls_textstyle))
                                          (vla-put-StyleName vnam_guide str_textstyle_gbo)
                                          )
                                        )
                                  "action_guidetext"
                                  )))
             (cons "NOEXPORT"(lambda()nil));;出力せず読み込み時にnilにする
             )
        
        (list(cons "SYMBOL" 'str_textstyle_gbo);;スタイルは2回やる
             (cons "INITIALFUNC" (lambda(a)(nth int_textstyle_gbo ls_textstyle)))
             (cons "NOEXPORT"(lambda()T));;出力せず読み込み時になにもしない
             )
        

        (list(cons "TEXT"(mix_strasc(list 12463 12522 12483 12463 25805 20316)) )
             (cons "ITEM" "POPUP_LIST");;ガイドテキストのクリック操作
             (cons "VALLIST"(mapcar 'mix_strasc(list(list 26377 21177)(list 28961 21177))))
             (cons "SYMBOL" 'int_guideclick)(cons "TYPE" "INT")
             (cons "INITIALFUNC" (lambda(a)0))
             )
        (list(cons "TEXT"(mix_strasc(list 12463 12522 12483 12463 12398 27178 26041 21521 26377 21177 31684 22258) ) )
             (cons "ITEM" "EDIT_BOX");;ガイドテキストクリックの横方向有効範囲
             (cons "EXPLANE"(mix_strasc(list 8251 9734 12398 31684 22258
                                             " ( " 12473 12479 12452 12523 12395 20381 23384 12377 12427 
                                             "  2 " 12391 20808 38957 25991 23383 31243 24230 " )") ))
             
             ;;星の範囲スタイル依存:2で先頭文字程度
             (cons "SYMBOL" 'width_guideclick)(cons "TYPE" "REAL")
             (cons "INITIALFUNC" (lambda(a)10.))
             )
        (list(cons "TEXT"(mix_strasc(list 12486 12461 12473 12488 12469 12452 12474)))
             (cons "EXPLANE"(mix_strasc(list 8251 30011 38754 27604 ) ))
             (cons "ITEM" "EDIT_BOX")
             (cons "SYMBOL" 'textsize_guide_bo)(cons "TEMP" 'textsize_guide_bo_temp)
             (cons "TYPE" "REAL")(cons "INITIALFUNC"(lambda(a)0.015)) )
        
        (list(cons "TEXT"(mix_strasc(list  32294 26041 21521 20301 32622)))
             ;;画面の左上を0とする,単位は1行当たりのテキスト高さ
             (cons "EXPLANE"(mix_strasc(list 8251 30011 38754 12398 24038 19978 12364 "0(" 21336 20301 12399 "1" 34892 24403 12383 12426 12398 12486 12461 12473 12488 39640 12373 ")" )))
             (cons "ITEM" "EDIT_BOX")
             (cons "SYMBOL" 'y_guidebase)(cons "TEMP" 'y_guidebase_temp)
             (cons "TYPE" "REAL") (cons "INITIALFUNC"(lambda(a)-2.))
             )
        
        (list(cons "TEXT"(mix_strasc(list 25968 20516 20837 21147 12434 12510 12454 12473 12391  21046 24481  )) )
             (cons "ITEM" "POPUP_LIST");;数値入力をマウスで制御,しない,左右,上下
             (cons "EXPLANE"(mix_strasc(list 8251 30906 23450 12399 21491 12463 12522 12483 12463
                                             "(" 24038 12463 12522 12483 12463 12391 22793 26356 21069 12398 20516 12395 25147 12377 ")")))
             ;;※確定は右クリック,左クリックで変更前の値に戻す
             (cons "VALLIST"
                   (mapcar 'mix_strasc(list(list 12375 12394 12356)(list 24038 21491)(list 19978 19979))))
             (cons "SYMBOL" 'int_controleinputval)(cons "TYPE" "INT")
             (cons "INITIALFUNC" (lambda(a)0))
             )

        (list(cons "TEXT"(mix_strasc(list 12510 12454 12473 21046 24481 12398 12392 12365 20024 12417 26689  )) )
             (cons "ITEM" "EDIT_BOX");;マウス制御のとき丸め桁
             (cons "SYMBOL" 'int_roundcontroleval)
             (cons "TYPE" "INT")(cons "INITIALFUNC"(lambda(a)0))
             )
        
   
        ;; (list(cons "TEXT"(mix_strasc(list 12463 12522 12483 12463 25805 20316)) );;背景マスク
        ;;      (cons "ITEM" "POPUP_LIST")
        ;;      (cons "VALLIST"(mapcar 'mix_strasc(list(list 12394 12375)(list 12354 12426 ))))
        ;;      (cons "SYMBOL" 'int_guidemask)(cons "TYPE" "INT")
        ;;      (cons "INITIALFUNC" (lambda(a)0))
        ;;      )


        (list(cons "TEXT"(mix_strasc(list 12304 12381 12398 20182 "UI" 35373 23450 12305)))
             (cons "ITEM" "TEXT"))

        (list(cons "TEXT"(mix_strasc(list 35686 21578 25991 12398 20986 12375 26041 )) )
             (cons "ITEM" "POPUP_LIST");;警告文の出し方
             (cons "EXPLANE"(mix_strasc(list 8251 12480 12452 12450 12525 12464 25805 20316 26178 12398 35686 21578 12399 12509 12483 12503 12450 12483 12503 12398 12415 )));;ダイアログ操作時の警告はポップアップのみ
             (cons "VALLIST"(mapcar 'mix_strasc(list(list 12509 12483 12503 12450 12483 12503)
                                                    (list 12467 12510 12531 12489 12521 12452 12531 ))))
             (cons "SYMBOL" 'int_alert)(cons "TYPE" "INT")
             (cons "INITIALFUNC" (lambda(a)0))
             (cons "BREAK" 0)
             )

        (list(cons "TEXT"(mix_strasc(list 12304 31649 36335 20316 25104  12305)))
             (cons "ITEM" "TEXT"))
        
        (list(cons "TEXT"(mix_strasc(list 22320 34920 38754 27161 39640)))
             (cons "ITEM" "BUTTON");;地表面標高
             (cons "BUTTONLABEL"(mix_strasc(list 36984 25246)))
             (cons "SYMBOL" 'str_lasground);;(cons "TYPE" "STR");;BUTTONのときいらない
             (cons "ACTION"
                   ((lambda()
                      (setq action_buttonground
                            (lambda() (setq func_next settile_selectground)))
                      "action_buttonground")))
             (cons "NOEXPORT"(lambda()T))
             ;;INITIALTYPE;;INITIALFUNC
             )
        (list(cons "SYMBOL" 'height_ground)
             (cons "NOEXPORT"(lambda()T)))
        
        (list(cons "TEXT"(mix_strasc(list 32218 24418 25237 24433 26178 12398 26368 22823 12500 12483 12481)))
             (cons "ITEM" "EDIT_BOX");;線形投影時の最大ピッチ
             (cons "EXPLANE"(mix_strasc(list 8251 "0" 12398 12392 12365 36984 25246 12375 12383 32218 12398 31680 28857 12398 12415 12434 25237 24433 12377 12427)))
             ;;0のとき選択した線の節点のみを投影する
             (cons "SYMBOL" 'pitch_project)(cons "TEMP" 'pitch_project_temp)
             (cons "TYPE" "REAL") (cons "INITIALFUNC"(lambda(a)0.5))
             )

        
        (list(cons "TEXT"(mix_strasc(list 25237 24433 32218 31680 28857 12398 20870 21322 24452  )))
             (cons "ITEM" "EDIT_BOX");;投影線節点の円半径
             (cons "SYMBOL" 'radius_node)(cons "TEMP" 'radius_node_temp)
             (cons "TYPE" "REAL") (cons "INITIALFUNC"(lambda(a)0.1))
             )

        (list(cons "TEXT"(mix_strasc(list 28145 24230 20837 21147 26041 27861 )))
             (cons "ITEM" "POPUP_LIST");;高度入力方法;;地表面標高差分,正負逆で差分入力,標高入力
             (cons "VALLIST"(setq ls_type_inputdepth
                                  (mapcar 'mix_strasc
                                          (list(list 27161 39640 24046 20998)
                                               (list 27161 39640 24046 20998
                                                     "(" 27491 36000 36870 ")")
                                               (list 27161 39640 20837 21147)
                                               ))))
             (cons "SYMBOL" 'int_inputdepth)(cons "TEMP" 'int_inputdepth_temp)
             (cons "TYPE" "INT") (cons "INITIALFUNC"(lambda(a)1)))
        
        (list(cons "TEXT"(mix_strasc(list 28145 24230 20837 21147 25163 38918   )))
             (cons "EXPLANE"(mix_strasc(list 8251 32076 36335 27770 23450 12398 12463 12522 12483 12463 24460 12398 25805 20316 12434 36984 25246)));;※経路決定のクリック後の操作を選択
             (cons "ITEM" "POPUP_LIST");;深度入力手順;;即時適用,深度の入力に移行,深度→オフセットの入力に移行
             (cons "VALLIST"(setq ls_type_editdepth
                                  (mapcar
                                   'mix_strasc
                                   (list(list 28145 24230 12398 20837 21147 12395 31227 34892)
                                        (list 28145 24230 8594 12458 12501 12475 12483 12488 12398 20837 21147)
                                        (list 21363 26178 36969 29992)
                                        ))))
             (cons "SYMBOL" 'int_editdepth);;(cons "TEMP" 'int_inputdepth_temp)
             (cons "TYPE" "INT") (cons "INITIALFUNC"(lambda(a)0)))

        
        (list(cons "TEXT"(mix_strasc(list 26354 12370 21322 24452 27770 23450 26041 27861 )))
             (cons "EXPLANE"(mix_strasc(list  8251 12300 30452 32218 31471 37096 12434 36890 12427 12301 12391 12399 20837 21147 20516 12399 19979 38480 20516 12392 12394 12427 ))) ;;※「直線端部を通る」では入力値は下限値となる
             (cons "ITEM" "POPUP_LIST");;曲げ半径決定方法,直線端部を通る,入力値を使用
             (cons "VALLIST"(setq ls_type_decidearc
                                  (mapcar
                                   'mix_strasc
                                   (list(list 30452 32218 31471 37096 12434 36890 12427)
                                        (list 20837 21147 20516 12434 20351 29992)
                                        ))))
             (cons "SYMBOL" 'int_editarcradius)(cons "TEMP" 'int_editarcradius_temp)
             (cons "TYPE" "INT") (cons "INITIALFUNC"(lambda(a)1)))
        
        (list(cons "TEXT"(mix_strasc(list  26032 35215 20870 24359 12398 35373 23450 20301 32622 )))
             (cons "EXPLANE"(mix_strasc(list 8251 "2" 22238 30446 20197 38477 12398 32232 38598 26178 12399 20219 24847 12395 35373 23450 12391 12365 12414 12377  )));;※2回目以降の編集時は任意に設定できます
             (cons "ITEM" "POPUP_LIST");;新規円弧の設定位置
             (cons "VALLIST"(setq ls_type_editarcposition
                                  (mapcar
                                   'mix_strasc;;手動,起点側終点を通過,終点側起点を通過
                                   (list(list 25163 21205)
                                        (list 36215 28857 20596 32066 28857 12434 36890 36942)
                                        (list 32066 28857 20596 36215 28857 12434 36890 36942)
                                        ))))
             (cons "SYMBOL" 'int_editarcposition);;(cons "TEMP" 'int_inputdepth_temp)
             (cons "TYPE" "INT") (cons "INITIALFUNC"(lambda(a)1)))
        
        (list(cons "TEXT"(mix_strasc(list 31649 12398 12514 12487 12522 12531 12464 )))
             (cons "ITEM" "POPUP_LIST");;管のモデリング
             (cons "VALLIST"(mapcar 'mix_strasc
                                    (list(list 12513 12483 12471 12517 )
                                         (list 12477 12522 12483 12489 ) )))
             (cons "SYMBOL" 'int_ductsolidmesh);;(cons "TEMP" 'int_protectcon_temp)
             (cons "TYPE" "INT") (cons "INITIALFUNC"(lambda(a)0)))
        
        (list(cons "TEXT"(mix_strasc(list 20445 35703 12467 12531 12463 12522 12540 12488 26377 28961)))
             (cons "ITEM" "POPUP_LIST");;保護コンクリート有無
             (cons "VALLIST"(setq ls_type_protect
                                  (mapcar 'mix_strasc
                                          (list(list 12354 12426 " ( " 20840 21608 " )")
                                               (list 12354 12426 " ( " 19979 21322 " )")
                                               (list 12394 12375)))))
             (cons "SYMBOL" 'int_protectcon)(cons "TEMP" 'int_protectcon_temp)
             (cons "TYPE" "INT") (cons "INITIALFUNC"(lambda(a)2))
             (cons "BREAK" 0)
             )
        
        (list(cons "SYMBOL" 'int_invisible_annotation)(cons "TYPE" "INT")
             (cons "INITIALFUNC"(lambda(a)0)) )
        
        (list(cons "TEXT"(mix_strasc(list "")))
             (cons "ITEM" "TEXT"))
        
        (list(cons "TEXT"(mix_strasc(list 31649 30452 24452))) 
             (cons "ITEM" "EDIT_BOX");;管直径
             (cons "SYMBOL" 'diam_duct)(cons "TEMP" 'diam_duct_temp)
             (cons "TYPE" "REAL")(cons "INITIALFUNC"(lambda(a)0.35)))
        (list(cons "TEXT"(mix_strasc(list 20445 35703 12467 12531 12463 12522 12540 12488 24133))) 
             (cons "ITEM" "EDIT_BOX");;保護コンクリート幅
             (cons "SYMBOL" 'width_protect)(cons "TEMP" 'width_protect_temp)
             (cons "TYPE" "REAL")(cons "INITIALFUNC"(lambda(a)0.5)))
        (list(cons "TEXT"(mix_strasc(list 20445 35703 12467 12531 12463 12522 12540 12488 39640 12373)))
             (cons "ITEM" "EDIT_BOX");;保護コンクリート高さ
             (cons "EXPLANE"(mix_strasc(list 8251 19979 21322 12398 12392 12365 12399 20837 21147 20516 12398 "0.5" 20493 12392 12394 12427 )))
             (cons "SYMBOL" 'height_protect)(cons "TEMP" 'height_protect_temp)
             (cons "TYPE" "REAL") (cons "INITIALFUNC"(lambda(a)0.5))
             )
        (list(cons "TEXT"(mix_strasc(list 20445 35703 12467 12531 12463 12522 12540 12488 38754 21462 12426)))
             (cons "ITEM" "EDIT_BOX");;保護コンクリート面取り
             (cons "SYMBOL" 'filet_protect)(cons "TEMP" 'filet_protect_temp)
             (cons "TYPE" "REAL") (cons "INITIALFUNC"(lambda(a)0.1)))
        (list(cons "TEXT"(mix_strasc(list 26354 32218 37096 12398 21322 24452)))
             (cons "ITEM" "EDIT_BOX");;曲線部の半径
             (cons "SYMBOL" 'radius_bend)(cons "TEMP" 'radius_bend_temp)
             (cons "TYPE" "REAL") (cons "INITIALFUNC"(lambda(a)5.))
             )

        (list(cons "TEXT"(mix_strasc(list 32076 36335 12364 12394 12356 12392 12365 12398 28145 24230 20837 21147 )))
             (cons "ITEM" "POPUP_LIST");;経路がないときの深度入力
             (cons "VALLIST"(mapcar 'mix_strasc;;許可しない
                                    (list(list 35377 21487 12375 12394 12356 )
                                         (list 35377 21487 12377 12427) )))
             (cons "SYMBOL" 'int_allow_noroad)(cons "TEMP" 'int_allow_noroad_temp)
             (cons "TYPE" "INT") (cons "INITIALFUNC"(lambda(a)0))
             )

        (list(cons "TEXT"(mix_strasc(list 12304 31649 36335 29305 27530 37096 20849 36890 12305)))
             (cons "ITEM" "TEXT"))
        
        (list(cons "SYMBOL" 'str_dimstyle_ductlevel)(cons "INITIALFUNC"(lambda(a)nil))
             (cons "EXPLANE"(mix_strasc(list 27161 39640 23544 27861 12473 12479 12452 12523)))
             )

        
        
        (list(cons "TEXT"(mix_strasc(list 27161 39640 23544 27861 12473 12479 12452 12523)))
             (cons "ITEM" "POPUP_LIST")(cons "VALLIST" ls_dimstyle);;標高寸法スタイル
             (cons "EXPLANE"(mix_strasc(list 8251 12371 12428 12363 12425 20316 25104 12373 12428 12427 12418 12398 12395 23550 12375 12390 26377 21177)))
             (cons "SYMBOL" 'int_dimstyle_ductlevel)(cons "TYPE" "INT")
             (cons "INITIALFUNC" (lambda(a)
                                   
                                   (if(if str_dimstyle_ductlevel
                                          (setq i(vl-position str_dimstyle_ductlevel ls_dimstyle)))T
                                     (if(setq i(vl-position "Standard" ls_dimstyle))T
                                       (setq i(vl-position(getvar "DIMSTYLE")ls_dimstyle)) ))
                                   i))
             
             (cons "ACTIONLIST"((lambda( / )
                                  (setq action_dimlevel
                                        (lambda(str / i)
                                          (setq i(atoi(get_tile str))
                                                int_dimstyle_ductlevel i
                                                str_dimstyle_ductlevel(nth i ls_dimstyle))
                                          )
                                        )
                                  "action_dimlevel"
                                  )))
             (cons "NOEXPORT"(lambda()nil))
             )
        
        (list(cons "SYMBOL" 'str_dimstyle_ductlevel)
             (cons "INITIALFUNC"(lambda(a)(nth int_dimstyle_ductlevel ls_dimstyle)))
             (cons "NOEXPORT"(lambda()T))
             )

        (list(cons "TEXT"(mix_strasc(list 27161 39640 20024 12417 26689 25968 ))) 
             (cons "ITEM" "EDIT_BOX");;標高丸め桁数
             (cons "SYMBOL" 'int_unitelevation);;
             (cons "TYPE" "INT") (cons "INITIALFUNC"(lambda(a)1)))

        (list(cons "TEXT"(mix_strasc(list  20870 24359 33258 21205 35336 31639 26178 20024 12417 26689 25968 ))) 
             (cons "ITEM" "EDIT_BOX");;円弧自動計算時丸め桁数
             (cons "SYMBOL" 'int_unitarcautoma);;
             (cons "TYPE" "INT") (cons "INITIALFUNC"(lambda(a)2)))
        
        (list(cons "TEXT"(mix_strasc(list 21517 31216 12398 19978 26360 12365 )));;
             (cons "ITEM" "POPUP_LIST")
             (cons "VALLIST"(mapcar 'mix_strasc(list(list 35377 21487 12375 12394 12356)
                                                    (list 35377 21487 12377 12427 ))))
             (cons "SYMBOL" 'int_allow_overwrite)(cons "TYPE" "INT")
             (cons "INITIALFUNC" (lambda(a)0))
             (cons "BREAK" 0)
             )
        
        ;; (list(cons "TEXT" "");;(mix_strasc(list 26354 32218 37096 38291 12398 30452 32218 37096 38263 12373)))
        ;;      ;; ;;曲線部間の直線部長さ
        ;;      ;; (cons "EXPLANE"(mix_strasc(list "0" 12424 12426 22823 12365 12356 12392 12365 30452 32218 37096 12434 12388 12394 12368 26354 32218 37096 12398 38291 12395 30452 32218 37096 12434 35373 12369 12427))) ;;0より大きいとき直線部をつなぐ曲線部の間に直線部を設ける
        ;;      (cons "ITEM" "TEXT");;"EDIT_BOX")
        ;;      (cons "SYMBOL" 'length_arccenter)(cons "TEMP" 'length_arccenter_temp)
        ;;      (cons "TYPE" "REAL") (cons "INITIALFUNC"(lambda(a)0.))
        ;;      )

        (list(cons "TEXT"(mix_strasc(list 12304 29305 27530 37096 20316 25104 12305)))
             (cons "ITEM" "TEXT"));;特殊部
        
        (list(cons "TEXT"(mix_strasc(list 22825 31471 12363 12425 22320 34920 38754 12414 12391)))
             (cons "ITEM" "EDIT_BOX");;特殊部天端から地表面まで
             (cons "EXPLANE"(mix_strasc(list 8251 65288 "=" 12510 12531 12507 12540 12523 31361 20986 38263 12373 65289))) ;;（=マンホール突出長さ）
             (cons "SYMBOL" 'height_ccboxtop)(cons "TEMP" 'height_ccboxtop_temp)
             (cons "TYPE" "REAL") (cons "INITIALFUNC"(lambda(a) 0.3))
             )
        (list(cons "TEXT"(mix_strasc(list 39640 12373)));;特殊部高さ
             (cons "ITEM" "EDIT_BOX")
             (cons "SYMBOL" 'height_ccbox)(cons "TEMP" 'height_ccbox_temp)
             (cons "TYPE" "REAL") (cons "INITIALFUNC"(lambda(a)2.)))
        
        (list(cons "TEXT"(mix_strasc(list 12510 12531 12507 12540 12523 30452 24452)))
             (cons "ITEM" "EDIT_BOX");; マンホール直径
             (cons "SYMBOL" 'diam_manhole)(cons "TEMP" 'diam_manhole_temp)
             (cons "TYPE" "REAL") (cons "INITIALFUNC"(lambda(a)0.9)))

        (list(cons "TEXT"(mix_strasc(list 22343 12375 12467 12531 12458 12501 12475 12483 12488)))
             (cons "ITEM" "EDIT_BOX");; 均しコンオフセット
             (cons "SYMBOL" 'offset_levelingcon)(cons "TEMP" 'offset_levelingcon_temp)
             (cons "TYPE" "REAL") (cons "INITIALFUNC"(lambda(a)0.05)))
        (list(cons "TEXT"(mix_strasc(list 22343 12375 12467 12531 39640 12373)))
             (cons "ITEM" "EDIT_BOX");; 均しコン高さ
             (cons "EXPLANE"(mix_strasc(list 8251 22343 12375 12467 12531 39640 12373 12364 "0" 12398 12392 12365 20316 25104 12373 12428 12394 12356 )));;0のとき作成されない
             (cons "SYMBOL" 'height_levelingcon)(cons "TEMP" 'height_levelingcon_temp)
             (cons "TYPE" "REAL") (cons "INITIALFUNC"(lambda(a)0.1))
             (cons "BREAK" 0)
             )

        (list(cons "TEXT"(mix_strasc(list 12304 26045 24037 30906 35469 38306 36899 12305)))
             (cons "ITEM" "TEXT"));;施工確認関連

        (list(cons "TEXT"(mix_strasc(list 24178 28169 35377 23481 20516)))
             (cons "ITEM" "EDIT_BOX");; 干渉許容値
             (cons "EXPLANE"(mix_strasc(list 8251 12431 12378 12363 12394 24178 28169 12434 35377 12377 12392 12365 36000 12398 20516 12434 20837 21147 )));;※わずかな干渉を許すとき負の値を入力
             (cons "SYMBOL" 'allow_influence)(cons "TEMP" 'allow_influence_temp)
             (cons "TYPE" "REAL") (cons "INITIALFUNC"(lambda(a)0.01)))
        
        (list(cons "TEXT"(mix_strasc(list 22303 34987 12426 35377 23481 20516)))
             (cons "ITEM" "EDIT_BOX");; 土被り許容値
             (cons "EXPLANE"(mix_strasc(list 8251 22303 34987 12426 35377 23481 20516 20197 19978 12398 12418 12398 12399 34920 31034 12373 12428 12394 12356))) ;; 土被り許容値以上のものは表示されない
             (cons "SYMBOL" 'allow_cover)(cons "TEMP" 'allow_cover_temp)
             (cons "TYPE" "REAL") (cons "INITIALFUNC"(lambda(a)0.5))
             )

        (list(cons "TEXT"(mix_strasc(list 31649 36335 25496 21066 12398 27861 21246 37197 )))
             (cons "ITEM" "EDIT_BOX");;管路掘削の法勾配
             (cons "EXPLANE"(mix_strasc(list 8251 12300 "1:X" 12301 12398 "X" 12398 20516 )));;「1:X」のXの値
             (cons "SYMBOL" 'ratio_excavation)(cons "TEMP" 'ratio_excavation_temp)
             (cons "TYPE" "REAL") (cons "INITIALFUNC"(lambda(a)0.))
             )
        
        (list(cons "TEXT"(mix_strasc(list 31649 36335 25496 21066 12398 27700 24179 26041 21521 38626 38548)))
             (cons "ITEM" "EDIT_BOX");;管路掘削の水平方向離隔
             (cons "EXPLANE"(mix_strasc(list 8251 31649 12414 12383 12399 20445 35703 12467 12531 12398 26368 22806 32257 12363 12425 27861 23611 12414 12391 12398 36317 38626 )));;管または保護コンの最外縁から法尻までの距離
             (cons "SYMBOL" 'offset_excavation)(cons "TEMP" 'offset_excavation_temp)
             (cons "TYPE" "REAL") (cons "INITIALFUNC"(lambda(a)0.1))
             )
        
        (list(cons "TEXT"(mix_strasc(list 31649 36335 25496 21066 12398 37467 30452 26041 21521 38626 38548)))
             (cons "ITEM" "EDIT_BOX");;管路掘削の鉛直方向離隔
             (cons "EXPLANE"(mix_strasc(list 8251 31649 12414 12383 12399 20445 35703 12467 12531 12398 26368 19979 31471 12363 12425 25496 21066 24213 38754 12414 12391 12398 36317 38626 )));;管または保護コンの最下端から掘削底面までの距離
             (cons "SYMBOL" 'separate_excavation)(cons "TEMP" 'separate_excavation_temp)
             (cons "TYPE" "REAL") (cons "INITIALFUNC"(lambda(a)0.1))
             )

        (list(cons "TEXT"(mix_strasc(list 31649 36335 25496 21066 12398 29983 25104 12500 12483 12481  )))
             (cons "ITEM" "EDIT_BOX");;管路掘削の生成ピッチ
             (cons "EXPLANE"(mix_strasc(list 8251 24179 38754 12395 12362 12369 12427 12500 12483 12481 )));;平面におけるピッチ
             (cons "SYMBOL" 'pitch_excavation)(cons "TEMP" 'pitch_excavation_temp)
             (cons "TYPE" "REAL") (cons "INITIALFUNC"(lambda(a)0.5))
             
             (cons "BREAK" 0)
             )
        
        
        ;; (list(cons "TEXT"(mix_strasc(list 22303 34987 12426 34920 31034 12500 12483 12481)))
        ;;      (cons "ITEM" "EDIT_BOX");; 土被り表示ピッチ
        ;;      (cons "EXPLANE"(mix_strasc(list 8251 22303 34987 12426 35377 23481 20516 "0" 12398 12392 12365 25351 23450 12375 12383 12500 12483 12481 12391 22303 34987 12426 12434 34920 31034 12377 12427))) ;;土被り許容値0のとき指定したピッチで土被りを表示する
        ;;      (cons "SYMBOL" 'pitch_cover)(cons "TEMP" 'pitch_cover_temp)
        ;;      (cons "TYPE" "REAL") (cons "INITIALFUNC"(lambda(a)2.))
        ;;      )

        (list(cons "TEXT"(mix_strasc(list 12304 33394 12392 30011 23652 35373 23450 12305)))
             (cons "ITEM" "TEXT"));;色と画層設定

        (list(cons "TEXT"(mix_strasc(list 12473 12490 12483 12503 12398 33394)))
             (cons "ITEM" "COLOR");; スナップの色
             (cons "SYMBOL" 'int_colsnappoint)(cons "TEMP" 'int_colsnappoint_temp)
             (cons "INITIALFUNC"(lambda(a)11)))

        
        (list(cons "TEXT"(mix_strasc(list 31649 12398 33394)))
             (cons "ITEM" "COLOR");; 管の色
             (cons "SYMBOL" 'int_colduct)(cons "TEMP" 'int_colduct_temp)
             (cons "INITIALFUNC"(lambda(a)1)))
        (list(cons "TEXT"(mix_strasc(list 32076 36335 12434 36984 25246 12375 12383 12392 12365 )))
             (cons "ITEM" "POPUP_LIST");;経路を選択したとき;;色を取得するしない
             (cons "VALLIST"(mapcar 'mix_strasc(list(list 33394 12434 21462 24471 12377 12427  )
                                                    (list 33394 12434 21462 24471 12375 12394 12356 ))))
             (cons "SYMBOL" 'int_getcolor_ductroad)(cons "TYPE" "INT")
             (cons "INITIALFUNC" (lambda(a)0))
             )

        (list(cons "TEXT"(mix_strasc(list 31649 12398 23544 27861 12398 33394)))
             (cons "ITEM" "COLOR");; 管の寸法の色
             (cons "SYMBOL" 'int_colductdim)(cons "TEMP" 'int_colductdim_temp)
             (cons "INITIALFUNC"(lambda(a)7)))

        (list(cons "TEXT"(mix_strasc(list 32232 38598 20013 12398 31649 12398 23544 27861 12398 33394)))
             (cons "ITEM" "COLOR");; 編集中の管の寸法の色
             (cons "SYMBOL" 'int_colductdimedit)(cons "TEMP" 'int_colductdimedit_temp)
             (cons "INITIALFUNC"(lambda(a)3)))
        
        (list(cons "TEXT"(mix_strasc(list 20445 35703 12467 12531 12398 33394)))
             (cons "ITEM" "COLOR");; 保護コンの色
             (cons "SYMBOL" 'int_colprotect)(cons "TEMP" 'int_colprotect_temp)
             (cons "INITIALFUNC"(lambda(a)9)))

        (list(cons "TEXT"(mix_strasc(list 25496 21066 27861 38754 12398 33394 )))
             (cons "ITEM" "COLOR");; 掘削法面の色
             (cons "SYMBOL" 'int_colexcavation)(cons "TEMP" 'int_colexcavation_temp)
             (cons "INITIALFUNC"(lambda(a)30)))
        ;; (list(cons "TEXT"(mix_strasc(list 20445 35703 12467 12531 12398 30011 23652 )))
        ;;      (cons "ITEM" "POPUP_LIST");;保護コンの画層
        ;;      (cons "VALLIST" ls_layername)
        ;;      (cons "SYMBOL" 'int_getcolor_ductroad)(cons "TYPE" "INT")
        ;;      (cons "INITIALFUNC" (lambda(a)0))
        ;;      )
        
        
        (list(cons "TEXT"(mix_strasc(list 29305 27530 37096 12398 33394)))
             (cons "ITEM" "COLOR");; 特殊部の色
             (cons "SYMBOL" 'int_colccbox)(cons "TEMP" 'int_colccbox_temp)
             (cons "INITIALFUNC"(lambda(a)8)))

        ;; (list(cons "TEXT"(mix_strasc(list 22303 34987 12426 "OK" 33394)))
        ;;      (cons "ITEM" "COLOR");; 土被りOK色
        ;;      (cons "SYMBOL" 'int_colcoverok)(cons "TEMP" 'int_colcoverok_temp)
        ;;      (cons "INITIALFUNC"(lambda(a)3)))
        
        (list(cons "TEXT"(mix_strasc(list 22303 34987 12426 "NG" 33394)))
             (cons "ITEM" "COLOR");; 土被りNG色
             (cons "SYMBOL" 'int_colcoverng)(cons "TEMP" 'int_colcoverng_temp)
             (cons "INITIALFUNC"(lambda(a)6)))

        (list(cons "TEXT"(mix_strasc(list 24178 28169 "NG" 33394)))
             (cons "ITEM" "COLOR");; 干渉NG色
             (cons "SYMBOL" 'int_colinfluence)(cons "TEMP" 'int_colinfluence_temp)
             (cons "INITIALFUNC"(lambda(a)11))
             )


        
        )
   
   ls_initialparameters ls_ductparameters
   
   str_terraductsession "onlysession"
   )
  
  (setq path_dcl(if command_for_alter(vl-filename-mktemp ".dcl")
                  (vl-filename-mktemp "0" "0" ".dcl") )
        nn(strlen path_dcl) )
  (while(/=(substr path_dcl nn 1)"\\")(setq nn(1- nn)))
  (setq str_path_tempdirectory(substr path_dcl 1 nn) )

  (setq bool_loop T)
  (while bool_loop;;whileである意味がなくなったが残す
    ((lambda( / point_view_center vec_x_onview vec_y_onview
                ls_screen_size_yx real_delta_x real_delta_y th point_base)
       (axd_function_read_session str_initialsession str_terraductsession)
       (if func_name
           (if(=(type func_name)'STR)
               (terraduct3d-menu func_name)
             (if(vl-position(type func_name)(list 'SUBR 'USUBR))
                 (func_name)
               )))
       ))
    )

  (vla-EndUndoMark (vla-get-ActiveDocument (vlax-get-Acad-Object)))
  (princ)
  )
  

;;FEATUREELEVSFROMSURF
(defun x-alert(lst / str)
  (setq str(mix_strasc lst))
  (if(= int_alert 0)(alert str)(princ(strcat "\n" str))))
(defun addkillobj(x)(setq ls_vnam_killobj(cons x ls_vnam_killobj)) )
(defun exckillobj(x)(setq ls_vnam_killobj(vl-remove x ls_vnam_killobj)) )

(defun terraduct3d-menu( str  / str ls_grfunc get_vnam_guide ls_guide_drawing )
  (setq str_edit str)
  (setq ls_vnam_highlight nil ls_vnam_visible nil ls_vnam_killobj nil)

  
  ((lambda( / oo xx yy)
     (setq oo(getvar "UCSORG")
           xx(getvar "UCSXDIR") yy (getvar "UCSYDIR")
           )
     (if(and(<(distance oo (list 0. 0. 0.))1e-8)
            (<(distance xx (list 1. 0. 0.))1e-8)
            (<(distance yy (list 0. 1. 0.))1e-8)
            )
         (setq olducsname nil)
       (progn
         (if bool_ucsexchangefirsttime
             ;;UCSがワールドではありません\nワールドでのみ実行可能なため変更します\nコマンド終了時に現在のものに戻します
             (x-alert(list "UCS" 12364 12527 12540 12523 12489 12391 12399 12354 12426 12414 12379 12435
                           "\n" 12527 12540 12523 12489 12391 12398 12415 23455 34892 21487 33021 12394 12383 12417 22793 26356 12375 12414 12377 
                           "\n" 12467 12510 12531 12489 32066 20102 26178 12395 29694 22312 12398 12418 12398 12395 25147 12375 12414 12377
                           ))
           )
         
         (setq bool_ucsexchangefirsttime nil)
         (setq olducsname (getvar "UCSNAME"))
         (if (= olducsname "")
             (progn
               (setq olducsname "__TEMP_UCS__")
               (command "_.UCS" "_Save" olducsname)
               (setq tempucs T))
           (setq tempucs nil))
         (command "_.UCS" "_World")
         ))
     ) )
  
  (setq 
   *error* ;;error_profile unique
   (lambda( msg )
     (done_dialog 0)
     (if(= msg "")T (vla-EndUndoMark (vla-get-ActiveDocument (vlax-get-Acad-Object))) )
     (mapcar '(lambda(a / v e);;オブジェクト
                (setq v(if(=(type a)'ENAME)(vlax-ename->vla-object a)a))
                (if(if(vl-catch-all-error-p 
                       (setq x(vl-catch-all-apply 'vlax-erased-p (list v))))
                       T x)
                    T
                  (vla-delete v) ))
             ls_vnam_killobj)
     (setq ls_vnam_killobj nil vnam_guide nil)

     (mapcar '(lambda(a / v e)
                (setq v(if(=(type a)'ENAME)(vlax-ename->vla-object a)a))
                (if(if(vl-catch-all-error-p 
                       (setq x(vl-catch-all-apply 'vlax-erased-p (list a))))
                       T x)
                    T
                  (vla-Highlight v :vlax-false)))
             ls_vnam_highlight)
     (setq ls_vnam_highlight nil)
     
     (mapcar '(lambda(a / v e x)
                (setq v(if(=(type a)'ENAME)(vlax-ename->vla-object a)a))
                (if(if(vl-catch-all-error-p 
                       (setq x(vl-catch-all-apply 'vlax-erased-p (list a))))
                       T x)
                    T
                  (vla-put-visible v :vlax-true)))
             ls_vnam_visible)
     (setq ls_vnam_visible nil)

     (mapcar '(lambda(lst / str sym val );;システム変数
                (setq str(car lst)sym(cadr lst))
                (if(setq val(eval sym))(setvar str val))
                (set sym nil) )
             (list(list "DELOBJ" 'temp_delobj)
                  (list "OSMODE" 'temp_obs)
                  (list "LOFTNORMALS" 'temp_loft)
                  (list "SELECTIONCYCLING" 'temp_selecycling)
                  (list "SELECTIONPREVIEW" 'temp_selepreview)
                  ))
     
     (mapcar '(lambda(a /  val x);;リリース
                
                (if(if(vl-catch-all-error-p 
                       (setq x(vl-catch-all-apply 'vlax-object-released-p  (list a))))
                       T x)
                    T
                  (vlax-release-object a))
                )
             ls_vla-release )
     (setq ls_vla-release nil)
     
     (setq bool_noeditdepth nil)
     
     ;;XRECORD保存
     ;; (mapcar
     ;;  '(lambda(lst / num array_data array_type str ls_hand)
     ;;     (if(setq ls_hand(eval(cdr lst)))
     ;;         (progn
     ;;           (setq str(car lst)num(length ls_hand)
     ;;                 array_data(vlax-make-safearray vlax-vbVariant(cons 0(1- num)))
     ;;                 array_type(vlax-make-safearray vlax-vbInteger(cons 0(1- num))) )
     ;;           (vlax-safearray-fill array_type(mapcar '(lambda(a)1005)ls_hand))
     ;;           (vlax-safearray-fill array_data ls_hand)
     ;;           (vla-SetXRecordData(vla-Item asis_session str)
     ;;                              array_type array_data )
     ;;           )))
     ;;  ls_duct_xrecords)

     (if olducsname
         (progn
           (command "_.UCS" "_Restore" olducsname)
           (if tempucs
               (command "_.UCS" "_Delete" olducsname))
           ))
     
     (vla-Regen(vla-get-ActiveDocument(vlax-get-acad-object))acAllViewports)
     
     (redraw)
     (gc)
     (setq *error*(lambda(msg)(princ msg)))
     (princ msg)
     )
   )

  (mapcar '(lambda(lst / sym str val)
             (setq str(car lst)sym(cadr lst)val(caddr lst))
             ;;CADによって存在しない変数があるため保護する
             (if(vl-catch-all-error-p
                 (vl-catch-all-apply '(lambda()(set sym(getvar str))(setvar str val))nil))
                 (set sym nil)))
          (list(list "SELECTIONCYCLING" 'temp_selecycling -2)
               ;;ロールオーバープレビューを止める。
               ;;  ガイド文字(vnam_guide)は実体のあるMTEXTなので、
               ;;  ダイアログ(地表面標高のDCL等)を挟むとその後のgrread中も
               ;;  プレビューが働き続けることがあり、マウスを重ねると
               ;;  ハイライトされていた。終了時に元へ戻す
               (list "SELECTIONPREVIEW" 'temp_selepreview 0)
               ))
  
  (setq vnam_blockTable(vla-get-blocks(vla-get-ActiveDocument (vlax-get-acad-object)))
        ls_vla-release(list vnam_blockTable ));;errorよりあとにやる

  ;;asissession
  (setq ls_vnam_killobj nil int_guidemask 0)

  (setq vnam_guide
        ((lambda( /  entna vnam )
           (setq entna(entmakex
                       (append
                        (list(cons 0 "MTEXT")(cons 100 "AcDbEntity")(cons 100 "AcDbMText")
                             (cons 7 str_textstyle_gbo)(cons 62 255)(cons 40 0.01 )(list 10 0 0 0)
                             (cons 1 "AAAAAAAAA")(cons 71 1)
                             )
                        (if(= int_guidemask 1)
                            ;;(list(cons 90 1)(cons 63 177)(cons 421 986966)(cons 45 2.))
                            (list(cons 90 3)(cons 63 256)(cons 45 2.))
                          )
                        ))
                 vnam(vlax-ename->vla-object entna))
           (addkillobj vnam)
           vnam))
        )

  (setq vnam_cross_temp
        (vla-addline(vla-get-modelspace(vla-get-activedocument(vlax-get-acad-object)))
                    (vlax-3d-point 0. 0. 0.)(vlax-3d-point 0. 0. 0.))
        )
  (addkillobj vnam_cross_temp)
  (vla-put-visible vnam_cross_temp :vlax-false)
  
  (axd_command_initial grfunc_duct3d)
  
  (progn ;;unique
    (setq ls_booleditunique
          (list "home" "home"))
    (setq ls_lasgrid(list))
    (vlax-for
     vnam dicts_all
     (if(vl-catch-all-error-p
         (setq str(vl-catch-all-apply 'vla-get-name (list vnam))))
         (setq str nil)
       (if(vl-string-search "lasgrid-" str)
           (setq ls_lasgrid(cons(cons str vnam)ls_lasgrid )))
       )
     )

    (setq str_layprotect(mix_strasc(list 20445 35703 12467 12531 12463 12522 12540 12488 )))
    (entdel(entmakex(list(cons 0 "POINT")(list 10 0 0 0)(cons 8 str_layprotect))))
    
    (progn ;;ground
      (setq path_selectgrounddcl(strcat str_path_tempdirectory "selectground.dcl") 
            open_file (open path_selectgrounddcl "w")
            )
      (write_strlist
       open_file
       (list
        "Sedit :dialog"
        "{"
        (mix_strasc;;地形選択
         (list " label = \""  22320 24418 36984 25246 "\";"))

        (list_to_dcltext;;一定標高で入力
         (list "text"(cons "width" "30")(cons "fixed_width" "true")
               (cons "value"(mix_strasc(list 19968 23450 27161 39640 12391 20837 21147)))))
        (list_to_dcltext
         (list "edit_box"(cons "width" "10")(cons "fixed_width" "true")
               (cons "key" "groundvalue")))
        " spacer;"
        (list_to_dcltext;;入力済みデータから選択
         (list "text"(cons "width" "30")(cons "fixed_width" "true")
               (cons "value"(mix_strasc(list 20837 21147 28168 12415
                                             12487 12540 12479 12363 12425 36984 25246)))))
        (list_to_dcltext
         (list "list_box"(cons "width" "20")(cons "height" "10")
               (cons "key" "groundlas")))

        " :row"
        " {"
        "  alignment = left;"
        "  fixed_width = true;"
        "  fixed_height = true;"
        
        (list_to_dcltext;;;;入力データをブロック化
         (list "text"(cons "width" "20")(cons "fixed_width" "true")
               (cons "value"(mix_strasc(list  20837 21147 12487 12540 12479 12434 12502 12525 12483 12463 21270)))))
        (list_to_dcltext;;;;入力データをブロック化
         (list "popup_list"(cons "width" "20")(cons "fixed_width" "true")
               (cons "key" "insertblock") ))
        "  }"
        
        " :row"
        " {"
        "  alignment = left;"
        "  fixed_width = true;"
        (list_to_dcltext;;データをグリッドとして読込
         (list "button"(cons "width" "16")(cons "fixed_width" "true")
               (cons "key" "inputlas")
               (cons "label"(mix_strasc(list "las" 12487 12540 12479 12434 12464 12522 12483 12489 12392 12375 12390 35501 36796)))))

        (list_to_dcltext;;データを
         (list "button"(cons "width" "16")(cons "fixed_width" "true")
               (cons "key" "inputxml")
               (cons "label"(mix_strasc(list "xml" 12487 12540 12479 12434 12464 12522 12483 12489 12392 12375 12390 35501 36796)))))
        "  }"
        
        
        (list_to_dcltext;;ブロックを作成しなくてもグリッドの情報は内部データとして保存され使用できます
         (list "text"(cons "width" "65")(cons "fixed_width" "true")
               (cons "value"(mix_strasc(list 8251  12502 12525 12483 12463 12434 20316 25104 12375 12394 12367 12390 12418 12464 12522 12483 12489 12398 24773 22577 12399 20869 37096 12487 12540 12479 12392 12375 12390 20445 23384 12373 12428 20351 29992 12391 12365 12414 12377 )))))

        (list_to_dcltext;;ブロック作成の有無は処理時間に大きく影響するため注意してください
         (list "text"(cons "width" "65")(cons "fixed_width" "true")
               (cons "value"(mix_strasc(list 8251 12502 12525 12483 12463 20316 25104 12398 26377 28961 12399 20966 29702 26178 38291 12395 22823 12365 12367 24433 38911 12377 12427 12383 12417 27880 24847 12375 12390 12367 12384 12373 12356  )))))

        (list_to_dcltext;;ブロックを作成しても挿入しなかった場合、(0,0,0)に挿入すれば復元できます
         (list "text"(cons "width" "65")(cons "fixed_width" "true")
               (cons "value"(mix_strasc(list 8251  12502 12525 12483 12463 12434 20316 25104 12375 12390 12418 25407 20837 12375 12394 12363 12387 12383 22580 21512 12289 )))))

         (list_to_dcltext;;入力ファイル名がついたブロック定義を探し、(0,0,0)に挿入すれば復元できます
          (list "text"(cons "width" "65")(cons "fixed_width" "true")
                (cons "value"(mix_strasc(list 12288 12288 20837 21147 12501 12449 12452 12523 21517 12364 12388 12356 12383 12502 12525 12483 12463 23450 32681 12434 25506 12375 12289 "(0,0,0)" 12395 25407 20837 12377 12428 12400 24489 20803 12391 12365 12414 12377 )))))
         
        

        (list_to_dcltext;;※数値とデータどちらも入力されているときはデータを優先します
         (list "text"(cons "width" "65")(cons "fixed_width" "true")
               (cons "value"(mix_strasc
                             (list 8251 25968 20516 12392 12487 12540 12479
                                   12393 12385 12425 12418 20837 21147
                                   12373 12428 12390 12356 12427 12392 12365 12399
                                   12487 12540 12479 12434 20778 20808 12375 12414 12377)))))
        
        " ok_cancel;"
        " }";//end
        )
       )
      
      (close open_file)

      (setq settile_selectground
            (lambda( / func_las bool_loop str_inputdata)
              (setq bool_loop T)
              (while bool_loop
                (setq load_dcl (load_dialog path_selectgrounddcl))
                (new_dialog "Sedit" load_dcl)

                (setq addlist_las
                      (lambda(a)
                        (start_list "groundlas")
                        (mapcar 'add_list
                                (cons ""(mapcar '(lambda(a)
                                                   (vl-string-subst "" "lasgrid-"(car a)))
                                                ls_lasgrid)))
                        (end_list)
                        (set_tile "groundlas" (itoa(1+(if a a -1))))
                        
                        (start_list "insertblock")
                        (mapcar 'add_list
                                (mapcar 'mix_strasc
                                        (list;;作成しない,作成して挿入,作成して挿入しない
                                         (list 20316 25104 12375 12394 12356)
                                         (list 20316 25104 12375 12390 25407 20837)
                                         (list 20316 25104 12375 12390 25407 20837 12375 12394 12356)
                                         )))
                        (end_list)
                        )
                      accept_datainput
                      (lambda(n)
                        (setq str_inputdata(if(= n 0)"las" "xml"))
                        ;;(setq func_las(if(= n 0)load_las_to_grid load_xml_to_grid))
                        (setq int_inputlasinsert(atoi(get_tile "insertblock")))
                        (done_dialog 1)
                        )
                      
                      )


                
                (addlist_las(vl-position str_lasground ls_lasgrid))
                (set_tile "groundvalue"(if height_ground(as-numstr height_ground)""))
                
                (action_tile "inputlas" "(accept_datainput 0)")
                (action_tile "inputxml" "(accept_datainput 1)")
                ;; (mode_tile "inputxml" 1)
                
                (setq accept_ground
                      (lambda( / num val str bool_lay lst str_name bool)
                        (setq num(1-(as-atoi(get_tile "groundlas")))
                              str(get_tile "groundvalue"))
                        (if(if(> num -1)(setq str_name(car(nth num ls_lasgrid))))
                            (setq str_lasground str_name height_ground nil)
                          (if(/= str "")
                              (setq height_ground(atof str)str_lasground nil)
                            (setq bool T)))
                        
                        (if bool
                            (alert(mix_strasc(list 20309 12418 20837 21147 12373 12428 12390 12356 12414 12379 12435)))
                          (done_dialog 1))
                        )
                      )

                
                (action_tile "accept" "(accept_ground)")
                (setq dialog-box (start_dialog))
                (unload_dialog load_dcl)
                
                (if str_inputdata(setq height_ground nil str_lasground(load_las_to_grid str_inputdata)) )
                ;;(if func_las(setq height_ground nil str_lasground(func_las)) )
                
                (if(or str_lasground height_ground) (setq bool_loop nil)
                  (if(=(getvar "DIASTAT")0)
                      (progn ;;設定なしでキャンセルします\nモデル作成には標高の設定が必要なので必ず行ってください
                        (alert(mix_strasc(list 35373 23450 12394 12375 12391 12461 12515 12531 12475 12523 12375 12414 12377 "\n" 12514 12487 12523 20316 25104 12395 12399 27161 39640 12398 35373 23450 12364 24517 35201 12394 12398 12391 24517 12378 34892 12387 12390 12367 12384 12373 12356 )))
                        (setq bool_loop nil)
                        ))
                  )
                )

              ((lambda( / array_type array_data )
                 (setq xrec(vl-catch-all-apply 'vla-Item (list asis_session "PARAMETER")))
                 (vla-GetXRecordData xrec 'array_type 'array_data )
                 (setq lst(if array_data
                              (mapcar 'vlax-variant-value
                                      (vlax-safearray->list array_data)))
                       lst(split_list 2 lst)
                       )

                 (mapcar '(lambda(sym val / str)
                            (if val
                                (setq str(vl-symbol-name sym)
                                      lst(subst(list str val)(assoc str lst)lst)))
                            )
                         '(str_lasground height_ground)
                         (list str_lasground height_ground)
                         )
                 (setq lst(apply 'append lst))
                 
                 (setq lst(mapcar
                           '(lambda(val / sym str int_type str_type)
                              (setq str_type(type val))
                              (cons(if(= str_type 'REAL)1040
                                     (if(= str_type 'INT)1071
                                       (if(= str_type 'STR)1000
                                         )))
                                   val)
                              )
                           lst)
                       array_data(vlax-make-safearray
                                  vlax-vbVariant(cons 0(1-(length lst))))
                       array_type(vlax-make-safearray
                                  vlax-vbInteger(cons 0(1-(length lst))))
                       )
                 (vlax-safearray-fill array_type(mapcar 'car lst))
                 (vlax-safearray-fill array_data(mapcar 'cdr lst))
                 (vla-SetXRecordData xrec array_type array_data )
                 ))
              
              )
            )
      
      )

    
    

    (setq
     point_guide_center nil
     func_loopunique
     (lambda( / dict xrec )
       (if point_guide_center T
         (cond
          ((if str_lasground(setq dict(cdr(assoc str_lasground ls_lasgrid))))
           (if(vl-catch-all-error-p
               (setq xrec(vl-catch-all-apply 'vla-Item (list dict "GRID-SIZE_CENTER"))))
               T
             (progn
               (vla-GetXRecordData xrec 'array_type 'array_data )
               (if array_data
                   (setq z_ave
                         (cadr(mapcar 'vlax-variant-value
                                      (vlax-safearray->list array_data)))
                         point_guide_center(carxyz(getvar "VIEWCTR")z_ave)
                         )
                 )
               ))
           )
          (height_ground
           (setq point_guide_center(carxyz(getvar "VIEWCTR")height_ground))
           )
          )
         )
       
       )
     )
    );;unique

  
  ;;uniqueじゃない
  (setq path_addattributedcl(axd_make_dcl_attribute str_path_tempdirectory));;属性
  (axd_make_dcl_basesetting asis_session)
  (axd_command_loop)
  (*error* "")
  )


(defun grfunc_duct3d( / )
  (list
   
   (list
    "exit"
    (cons "INITIAL"(lambda(bool)(if(car bool)(setq bool_loop nil))(if(cadr bool) (list )))) )
   
   (list
    "tempdistlength" ;;edsym 33
    (cons
     "INITIAL"
     (lambda(bool)
       (if(car bool)
           (setq bool_point T
                 ls_guideexplane nil
                 p_tempdist0 nil p_tempdist1 nil ls_strtempdist(list)
                 ls_guidemenu nil bool_linedisp nil
                 
                 
                 func_guidemenu
                 (lambda()
                   (mix_strasc
                    (list "2" 28857 12434 12463 12522 12483 12463 12375 12390 36317 38626 12434 28204 12427 12371 12392 12364 12391 12365 12414 12377
                          "\n" 12300 "!" 12301 12461 12540 12434 25276 12377 12392 28204 12387 12383 31623 25152 12434 32218 20998 12458 12502 12472 12455 12463 12488 12392 12375 12390 29983 25104 12391 12365 12427 12514 12540 12489 12395 20999 12426 26367 12360 12364 12391 12365 12414 12377
                          "\n" 12371 12398 32218 20998 12399 12467 12510 12531 12489 32066 20102 26178 12395 21066 38500 12373 12428 12414 12377 ))
                   
                   )
                 )
         )
       (if(cadr bool) (list ))
       ))

    (cons
     "GUIDE"
     (lambda( / bool p);;(d- grdisp_
       (setq bool(if(=(type elem_grread)'LIST)p_tempdist0)
             p(if p_tempdist1 p_tempdist1 elem_grread) )
       (list "\n{\\C" str_gcol_g ";" 36317 38626 "}" 9 ":"(if bool(as-numstr(distance p_tempdist0 p))"");;距離
             "\n{\\C" str_gcol_g ";" 916 "X}" 9 ":" (if bool(as-numstr(-(car p)(car p_tempdist0)))"")
             "\n{\\C" str_gcol_g ";" 916 "Y}" 9 ":" (if bool(as-numstr(-(cadr p)(cadr p_tempdist0)))"")
             "\n{\\C" str_gcol_g ";" 916 "Z}" 9 ":" (if bool(as-numstr(-(caddr p)(caddr p_tempdist0))) "")
             "\n{\\C" str_gcol_c "; !}" 9 ": " 35336 28204 12375 12383 32218 12434
             12467 12510 12531 12489 32066 20102 26178 12414 12391
             " " 12304
             (if bool_linedisp (list "{\\C" str_gcol_y ";" 27531 12377 "}")
               (list "{\\C" str_gcol_c ";" 27531 12373 12394 12356 "}"))
             12305
             ;;計測した線をコマンド終了時まで残す残さない
             "\n{\\C" str_gcol_c "; S}" 9 ": "
             12473 12490 12483 12503 20999 26367
             "  " 12304 32 (if bool_snap "ON" "OFF") 32 12305
             "\n"  21491 12463 12522 12483 12463 ",Enter:" 25147 12427
             ;;右クリック,Enter:戻る
             )
       ))
    
    (cons
     "MOVE"
     (lambda()(if p_tempdist0 (grdraw p_tempdist0(if p_tempdist1 p_tempdist1 elem_grread) 2)) )
     )

    (cons
     "CLICK"
     (lambda( / );;(d- gr3_profile()
       (cond
        (bool_linedisp
         (setq p_tempdist0 elem_grread
               p_tempdist1(getpoint p_tempdist0)
               vnam(vla-addline
                    (vla-get-modelspace(vla-get-activedocument(vlax-get-acad-object)))
                    (vlax-3d-point p_tempdist0)(vlax-3d-point p_tempdist1))
               )
         (vla-put-color vnam 4)
         (addkillobj vnam)
         )
        ((null p_tempdist0)(setq p_tempdist0 elem_grread))
        ((null p_tempdist1)
         (setq p_tempdist1 elem_grread)
         (if bool_inputmeasure
             (setq str_inputmeasure(as-numstr(distance p_tempdist0 p_tempdist1))
                   bool_replacegrread T int_grread 2 elem_grread 13
                   bool_tempdistlength(vl-position str_editreturn(list "makeductmain"))
                   str_edit str_editreturn str_editreturn nil))
         )
        (T(setq p_tempdist0 elem_grread p_tempdist1 nil))
        )
       ))

    (cons
     "KEYBOAD"
     (lambda();;(d- gr2_profile()
       (cond
        ((or(= elem_grread 13)(= int_grread 25))
         (setq bool_inputmeasure nil)
         (setq str_edit str_editreturn str_editreturn nil ))
        ((vl-position elem_grread(list 33 65281 -255))
         ;;(list 65 97 65296 65313 -240 -223))
         (setq bool_linedisp(null bool_linedisp))
         )
        )
       ))
    
    )
   
   

   (list
    "home" ;;edsym editsymbol
    (cons
     "INITIAL"
     (lambda(bool);;initial
       (if(car bool)
           (setq bool_point nil 
                 bool_selectent nil bool_select nil int_selectmode nil
                 ls_ssget(list) xtype_ssget nil xdata_ssget nil

                 func_guidemenu
                 (lambda()
                   (mix_strasc;;各項目にカーソルを合わせて★のとき「？」を入力してください
                    (list 21508 38917 30446 12395 12459 12540 12477 12523 12434 21512 12431 12379 12390 9733 12398 12392 12365 12300 65311 12301 12434 20837 21147 12375 12390 12367 12384 12373 12356  )
                    ) )
                 
                 ls_guideexplane
                 (list)
                 
                 ls_guidemenu
                 (list
                  (list(list 49 ) ;;線形の投影
                       (cons "ITEM"(list 32218 24418 12398 25237 24433))
                       (cons "NEXTMODE" "projectlinear")
                       ;;平面図の線形などを選択して現在設定している標高に投影する
                       (cons "HELP"(lambda()(mix_strasc(list 24179 38754 22259 12398 32218 24418 12394 12393 12434 36984 25246 12375 12390 29694 22312 35373 23450 12375 12390 12356 12427 27161 39640 12395 25237 24433 12377 12427 ))))
                       )
                  (list(list 50 );;管路作成
                       (cons "ITEM"(list 31649 36335 20316 25104))
                       (cons "NEXTMODE" "makeductmain")
                       ;;管の中心が通る位置を設定した標高からの深さまたは標高自体を指定して管を作成する
                       (cons "HELP"(lambda()(mix_strasc(list 31649 12398 20013 24515 12364 36890 12427 20301 32622 12434 35373 23450 12375 12383 27161 39640 12363 12425 12398 28145 12373 12414 12383 12399 27161 39640 33258 20307 12434 25351 23450 12375 12390 31649 12434 20316 25104 12377 12427  ))))
                       )
                  (list(list 51 );;特殊部作成
                       (cons "ITEM"(list 29305 27530 37096 20316 25104))
                       (cons "NEXTMODE" "makeccboxmain")
                       ;;特殊部の角およびマンホール中心を指定して、現在設定している標高に合わせて配置する
                       (cons "HELP"(lambda()(mix_strasc(list 29305 27530 37096 12398 35282 12362 12424 12403 12510 12531 12507 12540 12523 20013 24515 12434 25351 23450 12375 12390 12289 29694 22312 35373 23450 12375 12390 12356 12427 27161 39640 12395 21512 12431 12379 12390 37197 32622 12377 12427 ))))
                       )

                  (list(list 82 );;地表面更新を反映
                       (cons "ITEM"(list 22320 34920 38754 26356 26032 12434 21453 26144 ))
                       (cons "NEXTMODE" "refreshground")
                       ;;オブジェクトの標高を現在設定されている地表面で更新する
                       (cons "HELP"(lambda()(mix_strasc(list 12458 12502 12472 12455 12463 12488 12398 27161 39640 12434 29694 22312 35373 23450 12373 12428 12390 12356 12427 22320 34920 38754 12391 26356 26032 12377 12427 ))))
                       )
                  
                  (list(list 65 );;情報を付与する
                       (cons "ITEM"(list 24773 22577 12434 20184 19982 12377 12427))
                       (cons "NEXTMODE" "addattribute")
                       ;;本コマンドで作成したオブジェクトに対し、属性情報や施工情報などを付与する
                       (cons "HELP"(lambda()(mix_strasc(list 26412 12467 12510 12531 12489 12391 20316 25104 12375 12383 12458 12502 12472 12455 12463 12488 12395 23550 12375 12289 23646 24615 24773 22577 12420 26045 24037 24773 22577 12394 12393 12434 20184 19982 12377 12427 ))))
                       )
                  
                  (list(list 81);;許容値を超える土被り、干渉確認
                       (cons "ITEM"(list 35377 23481 20516 12434 36229 12360 12427 22303 34987 12426 12289 24178 28169 30906 35469))
                       (cons "NEXTMODE" "influencecheck")
                       ;;作成した管路の土被り許容値を設定して、それより浅い箇所を表記する,管同士の干渉している箇所を表記する
                       (cons "HELP"(lambda()(mix_strasc(list  20316 25104 12375 12383 31649 36335 12398 22303 34987 12426 35377 23481 20516 12434 35373 23450 12375 12390 12289 12381 12428 12424 12426 27973 12356 31623 25152 12434 34920 35352 12377 12427 "\n" 31649 21516 22763 12398 24178 28169 12375 12390 12356 12427 31623 25152 12434 34920 35352 12377 12427 ))))
                       
                       )

                  (list(list 88);;特定の位置で土被り確認
                       (cons "ITEM"(list 29305 23450 12398 20301 32622 12391 22303 34987 12426 30906 35469 ))
                       (cons "NEXTMODE" "influencepoint")
                       ;;管路の特定の位置を指定して土被りを表示
                       (cons "HELP"(lambda()(mix_strasc(list 31649 36335 12398 29305 23450 12398 20301 32622 12434 25351 23450 12375 12390 22303 34987 12426 12434 34920 31034 ))))
                       
                       )

                  
                  (list(list 69);;管路掘削
                       (cons "ITEM"(list 31649 36335 25496 21066)  )
                       (cons "NEXTMODE" "excavation")
                       ;;管路を選択して掘削形状を作成する
                       (cons "HELP"(lambda()(mix_strasc(list 31649 36335 12434 36984 25246 12375 12390 25496 21066 24418 29366 12434 20316 25104 12377 12427 ))))
                       )
                  
                  (list(list 67 );;断面図(未実装)
                       (cons "ITEM"(list 26029 38754 22259 )  )
                       (cons "NEXTMODE" "profiledrawing")
                       ;;
                       (cons "HELP"(lambda()(mix_strasc(list  ))))
                       )
                  
                  (list(list 68 );;データの入出力
                       (cons "ITEM"(list 12487 12540 12479 12398 20837 20986 21147))
                       (cons "NEXTMODE" "savecsvifc")
                       ;;本コマンドで作成したオブジェクトの情報をCSV,IFCで出力する\n作成したCSVまたはそれを編集したものを読み込んでオブジェクトを再現する
                       (cons "HELP"(lambda()(mix_strasc(list 26412 12467 12510 12531 12489 12391 20316 25104 12375 12383 12458 12502 12472 12455 12463 12488 12398 24773 22577 12434 "CSV,IFC" 12391 20986 21147 12377 12427 "\n" 20316 25104 12375 12383 "CSV" 12414 12383 12399 12381 12428 12434 32232 38598 12375 12383 12418 12398 12434 35501 12415 36796 12435 12391 12458 12502 12472 12455 12463 12488 12434 20877 29694 12377 12427 ))))
                       )
                  
                  (list(list 83 );;基本設定
                       (cons "ITEM"(list 22522 26412 35373 23450))
                       (cons "LOADFUNCTION" settile_basicsetting)
                       ;;実行すると別ウィンドウが開くのでそこで内容を確認してください
                       ;;\nここで設定した値がデフォルト値となります\nここ以外で値を変更しても、コマンド再開時は基本的にデフォルト値を使用します
                       (cons "HELP"(lambda()(mix_strasc(list 23455 34892 12377 12427 12392 21029 12454 12451 12531 12489 12454 12364 38283 12367 12398 12391 12381 12371 12391 20869 23481 12434 30906 35469 12375 12390 12367 12384 12373 12356 "\n" 12371 12371 12391 35373 23450 12375 12383 20516 12364 12487 12501 12457 12523 12488 20516 12392 12394 12426 12414 12377 "\n" 12371 12371 20197 22806 12391 20516 12434 22793 26356 12375 12390 12418 12289 12467 12510 12531 12489 20877 38283 26178 12399 22522 26412 30340 12395 12487 12501 12457 12523 12488 20516 12434 20351 29992 12375 12414 12377   ))))
                       )

                  (list(list 72 );;寸法表示非表示
                       (cons "ITEM"(list 23544 27861 34920 31034 38750 34920 31034 ))
                       (cons "NEXTMODE" "visible_annotation")
                       ;; (cons "LOADFUNCTION" )
                       (cons
                        "STATUS"
                        (lambda( / bool_depth ii ls_out)
                          (mix_strasc
                           (if(= int_invisible_annotation 1)
                               (list "{\\C" str_gcol_y ";" 38750 34920 31034 "}")
                             (list "{\\C" str_gcol_c ";" 34920 31034 "}")
                             ))
                          )
                        )
                       ;;管路、特殊部の寸法表示を切り替える
                       (cons "HELP"(lambda()(mix_strasc(list 31649 36335 12289 29305 27530 37096 12398 23544 27861 34920 31034 12434 20999 12426 26367 12360 12427  ))))
                       )

                  (list(list 85 );;UNDO地点追加
                       (cons "ITEM"(list "UNDO" 22320 28857 36861 21152  ))
                       (cons "LOADFUNCTION"
                             (lambda( / entna)
                               (vla-delete vnam_guide)
                               (exckillobj vnam_guide)
                               
                               (vla-EndUndoMark (vla-get-ActiveDocument (vlax-get-Acad-Object)))
                               
                               (vla-StartUndoMark (vla-get-ActiveDocument (vlax-get-Acad-Object)))
                               (setq entna(entmakex
                                           (append
                                            (list(cons 0 "MTEXT")(cons 100 "AcDbEntity")(cons 100 "AcDbMText")
                                                 (cons 7 str_textstyle_gbo)(cons 62 255)(cons 40 0.01 )(list 10 0 0 0)
                                                 (cons 1 "AAAAAAAAA")(cons 71 1)
                                                 )
                                            (if(= int_guidemask 1)
                                                ;;(list(cons 90 1)(cons 63 177)(cons 421 986966)(cons 45 2.))
                                                (list(cons 90 3)(cons 63 256)(cons 45 2.))
                                              )
                                            ))
                                     vnam_guide(vlax-ename->vla-object entna))
                               (addkillobj vnam_guide)
                               (setq bool_replacegrread T int_grread 5 elem_grread(list 0 0 0)
                                     str_guide_prev "" vec_view_gr5loop nil)
                               
                               ))
                       ;;通常はコマンド終了後にUNDOするとコマンド実行開始時点まで戻ります
                       ;;\n戻る位置を追加することができます
                       
                       (cons "HELP"(lambda()(mix_strasc(list 36890 24120 12399 12467 12510 12531 12489 32066 20102 24460 12395 "UNDO" 12377 12427 12392 12467 12510 12531 12489 23455 34892 38283 22987 26178 28857 12414 12391 25147 12426 12414 12377  "\n" "UNDO" 12391 25147 12427 20301 32622 12434 36861 21152 12377 12427 12371 12392 12364 12391 12365 12414 12377 ))))
                       )


                  (if bool_geosearch_link
                      (list(list 71);;ジオサーチ連携
                       (cons "ITEM"(list  12472 12458 12469 12540 12481 36899 25658  ))
                       (cons "LOADFUNCTION" geo3d)
                       ;;準備中
                       (cons "HELP"(lambda()(mix_strasc(list 28310 20633 20013 ))))
                       )
                    )
                  
                  
                  (list(list "ENTER");;終了
                       (cons "ITEM"(list 32066 20102))
                       (cons "NEXTMODE" "exit")
                       
                       )
                  )

                 ls_guidemenu(vl-remove nil ls_guidemenu)
                 
                 ls_home_guide
                 (cons(list(cons "NEXTMODE" "home")
                           (cons "ITEM"(list 12513 12452 12531 12513 12491 12517 12540 )) )
                      ls_guidemenu)
                 ))
       
       (if(cadr bool)
           (progn
             (list ;;コマンドするたびに直すもの
              (list nil 'int_ductmode 0)
              (list nil 'int_ccboxmode 0)
              (list nil 'int_cancelduct 0)
              (list nil 'int_hidesolid 1)
              (list T 'int_projectnode 0)
              ;; (list nil 'int_colduct_temp nil)
              (list nil 'str_ductname nil)
              (list nil 'int_adddepth nil)
              ;; (list nil 'int_colduct_temp nil)
              ;; (list nil 'int_protectcon_temp nil)
              ;; (list nil 'radius_bend_temp nil)
              ;; (list nil 'radius_bend_temp nil)
              ;; (list nil 'diam_duct_temp nil)
              ;; (list nil 'width_protect_temp nil)
              ;; (list nil 'height_protect_temp nil)
              ;; (list nil 'filet_protect_temp nil)
              
              )

             
             ))
       ))

    ;;GUIDE,MOVE,CLICK,KEYBOAD
    )
   
   (list
    "projectlinear" ;;edsym
    (cons
     "INITIAL"
     (lambda(bool);;initial
       (if(car bool)
           (setq bool_point nil 
                 bool_selectent T bool_select T int_selectmode 0
                 ls_ssget(list(cons -4 "<OR")
                              (cons 0 "LINE,LWPOLYLINE,POLYLINE,ARC")
                              ;; (cons -4 "<AND")
                              ;; (cons 0 "INSERT")(list -3(list "terraduct3d"))
                              ;; (cons -4 "AND>")
                              (cons -4 "OR>")
                              )
                 
                 ls_ssgetinsert(list(cons 0 "INSERT")
                                    (cons -4 "<NOT")(list -3(list "terraduct3d"))(cons -4 "NOT>") )
                 xtype_ssget nil xdata_ssget nil
                 int_selectproject 0
                 int_reproject 0
                 int_projectmode 1 bool_clickproject nil
                 allow_joint nil
                 ls_vnam_projectcircle(list)
                 ls_vnam_templine(list)

                 
                 str_projectname nil
                 func_guidemenu
                 (lambda()
                   (mix_strasc
                    (if ls_vnam_select
                        (list "Enter" 12391 29694 22312 12398 36984 25246 12434 29694 22312 35373 23450 12375 12390 12356 12427 27161 39640 12395 25237 24433 12375 12414 12377 "\n" 27161 39640 12398 35373 23450 12364 12373 12428 12390 12356 12394 12356 12392 12365 23455 34892 12391 12365 12414 12379 12435 );;Enterで現在の選択を現在設定している標高に投影します\n標高の設定がされていないとき実行できません
                      (list 24179 38754 22259 12398 31649 36335 12398 32218 12434 36984 25246 12375 12390 12367 12384 12373 12356 ));;平面図の管路の線を選択してください
                    ) )
                 
                 ls_guideexplane
                 nil
                 
                 ls_guidemenu
                 (list
                  
                  (list(list 76);; 地表面標高
                       (cons "ITEM"(mix_strasc(list 22320 34920 38754 27161 39640)))
                       (cons "STATUS"
                             (lambda()
                               (if str_lasground
                                   (mix_strasc
                                    (list "{\\C" str_gcol_c ";" 12487 12540 12479 "} : "
                                          (vl-string-subst "" "lasgrid-" str_lasground)))
                                 (if height_ground
                                     (mix_strasc
                                      (list"{\\C" str_gcol_g ";" 27161 39640 "} : "
                                           (as-numstr height_ground)))
                                   (mix_strasc
                                    (list "{\\C" str_gcol_r ";"
                                          36984 25246 12373 12428 12390 12356 12414 12379 12435 "}"))
                                   ))
                               ))
                       (cons "LOADFUNCTION"(lambda()(settile_selectground)))
                       ;;使用する標高を\n-las読込\n-xml読込\n-一定標高の数値入力\nから選択できます
                       (cons "HELP"(lambda()(mix_strasc(list 20351 29992 12377 12427 27161 39640 12434 "\n- las" 35501 36796 "\n- xml" 35501 36796 "\n- " 19968 23450 27161 39640 12398 25968 20516 20837 21147 "\n" 12363 12425 36984 25246 12391 12365 12414 12377 ))))
                       )

                  
                  (list(list 49);;;;1:平面図を選択
                       (cons "ITEM"(list 24179 38754 22259 12434 36984 25246))
                       (cons "LOADFUNCTION"
                             (lambda()
                               (setq int_projectmode 1)
                               (setq bool_point nil bool_selectent T bool_select T int_selectmode 0
                                     ls_ssget(list(cons -4 "<OR")
                                                  (cons 0 "LINE,LWPOLYLINE,POLYLINE,ARC")
                                                  ;; (cons -4 "<AND")
                                                  ;; (cons 0 "INSERT")(list -3(list "terraduct3d"))
                                                  ;; (cons -4 "AND>")
                                                  (cons -4 "OR>")
                                                  )
                                     
                                     ls_ssgetinsert(list(cons 0 "INSERT")
                                                        (cons -4 "<NOT")
                                                        (list -3(list "terraduct3d"))
                                                        (cons -4 "NOT>") )
                                     xtype_ssget nil xdata_ssget nil
                                     )

                               (if ls_vnam_projectcircle
                                   (progn
                                     (mapcar '(lambda(vnam)
                                                (setq ls_vnam_select(vl-remove vnam ls_vnam_select))
                                                (exckillobj vnam)
                                                (vla-delete vnam)
                                                )
                                             ls_vnam_projectcircle)
                                     (setq ls_vnam_projectcircle nil)
                                     (mapcar 'exckillobj ls_vnam_templine)
                                     (mapcar 'vla-delete ls_vnam_templine)
                                     (setq ls_vnam_templine nil)
                                     ))

                               
                               ))
                       (cons "STATUS"
                             (lambda()(mix_strasc;;現在のモード
                                       (if(= int_projectmode 1)
                                           (list "{\\C" str_gcol_y ";" 29694 22312 12398 12514 12540 12489 "}" )
                                         (list "{\\C" str_gcol_c ";" 12514 12540 12489 22793 26356  "}" )
                                         ))))
                       ;;\n平面図に記載されている線分,ポリラインなどの線形オブジェクトを選択して投影します
                       ;;\n円弧を含むポリラインのとき、円弧上の点は投影されません
                       ;;\n元々の線分で節点であった箇所には円が作成されます
                       ;;\nブロック内の線も選択可能です
                       ;;\n単点が近接しているものは投影後に接続して一つながりになります

                       (cons "HELP"
                             (lambda()
                               (mix_strasc
                                (list 24179 38754 22259 12395 35352 36617 12373 12428 12390 12356 12427 32218 20998 "," 12509 12522 12521 12452 12531 12394 12393 12398 32218 24418 12458 12502 12472 12455 12463 12488 12434 36984 25246 12375 12390 25237 24433 12375 12414 12377
                                      "\n" 20870 24359 12434 21547 12416 12509 12522 12521 12452 12531 12398 12392 12365 12289 20870 24359 19978 12398 28857 12399 25237 24433 12373 12428 12414 12379 12435
                                      "\n" 20803 12293 12398 32218 20998 12391 31680 28857 12391 12354 12387 12383 31623 25152 12395 12399 20870 12364 20316 25104 12373 12428 12414 12377 
                                      "\n" 12502 12525 12483 12463 20869 12398 32218 12418 36984 25246 21487 33021 12391 12377
                                      "\n" 21336 28857 12364 36817 25509 12375 12390 12356 12427 12418 12398 12399 25237 24433 24460 12395 25509 32154 12375 12390 19968 12388 12394 12364 12426 12395 12394 12426 12414 12377
                                      )
                                )))
                       )

                  (list(list 50);;;;\n2:クリックした点を投影
                       (cons "ITEM"(list 12463 12522 12483 12463 12434 25237 24433
                                         " (Z" 36600 ")" ))
                       (cons "LOADFUNCTION"
                             (lambda()
                               (setq int_projectmode 2)
                               (if ls_vnam_select
                                   (progn
                                     (mapcar '(lambda(vnam)
                                                (vla-Highlight vnam :vlax-false)
                                                (setq ls_vnam_highlight(vl-remove vnam ls_vnam_highlight))
                                                )
                                             ls_vnam_select)
                                     (setq ls_vnam_select nil)
                                     ))
                               (setq bool_point T bool_selectent nil bool_select nil int_selectmode -1
                                     ls_ssget nil ls_ssgetinsert nil xtype_ssget nil xdata_ssget nil)

                               
                               ))
                       (cons "STATUS"
                             (lambda()(mix_strasc;;現在のモード
                                       (if(= int_projectmode 2)
                                           (list "{\\C" str_gcol_y ";" 29694 22312 12398 12514 12540 12489 "}" )
                                         (list "{\\C" str_gcol_c ";" 12514 12540 12489 22793 26356  "}" )
                                         ))))
                       ;;\nクリックするとその点から地表面へZ方向またはビュー方向に投影した位置に点ができ、
                       ;;\nそれをつないだ線を作成します
                       (cons "HELP"
                             (lambda()
                               (mix_strasc
                                (list "\n" 12463 12522 12483 12463 12377 12427 12392 12381 12398 28857 12363 12425 22320 34920 38754 12408 "Z" 26041 21521 12395 25237 24433 12375 12383 20301 32622 12395 28857 12364 12391 12365 12289
                                      "\n" 12381 12428 12434 12388 12394 12356 12384 32218 12434 20316 25104 12375 12414 12377 )
                                )))
                       )
                  
                  (list(list 51);;\n3:クリックした点を投影
                       (cons "ITEM"(list 12463 12522 12483 12463 12434 25237 24433
                                         " (" 12499 12517 12540  ")" ))
                       (cons "LOADFUNCTION"
                             (lambda()
                               (setq int_projectmode 3)
                               (if ls_vnam_select
                                   (progn
                                     (mapcar '(lambda(vnam)
                                                (vla-Highlight vnam :vlax-false)
                                                (setq ls_vnam_highlight(vl-remove vnam ls_vnam_highlight))
                                                )
                                             ls_vnam_select)
                                     (setq ls_vnam_select nil)
                                     
                                     ))
                               (setq bool_point T bool_selectent nil bool_select nil int_selectmode -1
                                     ls_ssget nil ls_ssgetinsert nil xtype_ssget nil xdata_ssget nil)
                               ))
                       (cons "STATUS"
                             (lambda()(mix_strasc;;現在のモード
                                       (if(= int_projectmode 3)
                                           (list "{\\C" str_gcol_y ";" 29694 22312 12398 12514 12540 12489 "}" )
                                         (list "{\\C" str_gcol_c ";" 12514 12540 12489 22793 26356  "}" )
                                         ))))
                       ;;\nクリックするとその点から地表面へZ方向またはビュー方向に投影した位置に点ができ、
                       ;;\nそれをつないだ線を作成します
                       (cons "HELP"
                             (lambda()
                               (mix_strasc
                                (list "\n" 12463 12522 12483 12463 12377 12427 12392 12381 12398 28857 12363 12425 22320 34920 38754 12408 12499 12517 12540 26041 21521 12395 25237 24433 12375 12383 20301 32622 12395 28857 12364 12391 12365 12289
                                      "\n" 12381 12428 12434 12388 12394 12356 12384 32218 12434 20316 25104 12375 12414 12377 
                                      )
                                )))
                       )

                  (list(list 52);;;;\n4:投影済みの線を更新
                       (cons "ITEM"(list 25237 24433 28168 12415 12398 32218 12434 26356 26032))
                       (cons "LOADFUNCTION"
                             (lambda()
                               (setq int_projectmode 4)
                               (setq bool_point nil bool_selectent T bool_select T int_selectmode 0
                                     ls_ssget(list(cons 0 "INSERT")(list -3(list "terraduct3d")) )
                                     ls_ssgetinsert nil

                                     xtype_ssget nil xdata_ssget nil
                                     )


                               

                               (if ls_vnam_projectcircle
                                   (progn
                                     (mapcar '(lambda(vnam)
                                                (setq ls_vnam_select(vl-remove vnam ls_vnam_select))
                                                (exckillobj vnam)
                                                (vla-delete vnam)
                                                )
                                             ls_vnam_projectcircle)
                                     (setq ls_vnam_projectcircle nil)
                                     (mapcar 'exckillobj ls_vnam_templine)
                                     (mapcar 'vla-delete ls_vnam_templine)
                                     (setq ls_vnam_templine nil)
                                     ))
                               
                               ))
                       
                       (cons "STATUS"
                             (lambda()(mix_strasc;;現在のモード
                                       (if(= int_projectmode 4)
                                           (list "{\\C" str_gcol_y ";" 29694 22312 12398 12514 12540 12489 "}" )
                                         (list "{\\C" str_gcol_c ";" 12514 12540 12489 22793 26356  "}" )
                                         ))))
                       ;;\n選択後Enterで作成したときと現在で地表面データが異なるとき新しいデータに合わせます
                       (cons "HELP"
                             (lambda()
                               (mix_strasc
                                (list 36984 25246 24460 "Enter" 12391  20316 25104 12375 12383 12392 12365 12392 29694 22312 12391 22320 34920 38754 12487 12540 12479 12364 30064 12394 12427 12392 12365 26032 12375 12356 12487 12540 12479 12395 21512 12431 12379 12414 12377)
                                
                                )))
                       )
                  
                  (list(list 53);;;;\n5:投影済みの線を結合
                       (cons "ITEM"(list 25237 24433 28168 12415 12398 32218 12434 32080 21512))
                       (cons "LOADFUNCTION"
                             (lambda()
                               (setq int_projectmode 5)
                               (setq bool_point nil bool_selectent T bool_select T int_selectmode 0
                                     ls_ssget(list(cons 0 "INSERT")(list -3(list "terraduct3d")) )
                                     ls_ssgetinsert nil
                                     xtype_ssget nil xdata_ssget nil
                                     )

                               (if ls_vnam_projectcircle
                                   (progn
                                     (mapcar '(lambda(vnam)
                                                (setq ls_vnam_select(vl-remove vnam ls_vnam_select))
                                                (exckillobj vnam)
                                                (vla-delete vnam)
                                                )
                                             ls_vnam_projectcircle)
                                     (setq ls_vnam_projectcircle nil)
                                     (mapcar 'exckillobj ls_vnam_templine)
                                     (mapcar 'vla-delete ls_vnam_templine)
                                     (setq ls_vnam_templine nil)
                                     ))
                               
                               ))
                       (cons "STATUS"
                             (lambda()(mix_strasc;;現在のモード
                                       (if(= int_projectmode 5)
                                           (list "{\\C" str_gcol_y ";" 29694 22312 12398 12514 12540 12489 "}" )
                                         (list "{\\C" str_gcol_c ";" 12514 12540 12489 22793 26356  "}" )
                                         ))))
                       ;;\n投影済みの線を複数選択し、その単点が近接しているとき結合します
                       (cons "HELP"
                             (lambda()
                               (mix_strasc
                                (list 36984 25246 24460 "Enter" 12391 25237 24433 28168 12415 12398 32218 12434 35079 25968 36984 25246 12375 12289 12381 12398 21336 28857 12364 36817 25509 12375 12390 12356 12427 12392 12365 32080 21512 12375 12414 12377 )
                                )))
                       )
                  
                  (list(list 54);;\n6:投影済みの線の名称、色を変更
                       (cons "ITEM"(list 25237 24433 28168 12415 12398 32218 12398 21517 31216 12289 33394 12434 22793 26356))
                       
                       (cons "LOADFUNCTION"
                             (lambda()
                               (setq int_projectmode 6)
                               (setq bool_point nil
                                     bool_selectent nil bool_select nil int_selectmode -1

                                     ls_ssget(list(cons 0 "INSERT")(list -3(list "terraduct3d")) )
                                     ls_ssgetinsert nil
                                     ;;xtype_ssget "PROJECT" xdata_ssget "terraduct3d"
                                     ls_ssget nil xtype_ssget nil xdata_ssget nil

                                     )

                               (if ls_vnam_projectcircle
                                   (progn
                                     (mapcar '(lambda(vnam)
                                                (setq ls_vnam_select(vl-remove vnam ls_vnam_select))
                                                (exckillobj vnam)
                                                (vla-delete vnam)
                                                )
                                             ls_vnam_projectcircle)
                                     (setq ls_vnam_projectcircle nil)
                                     (mapcar 'exckillobj ls_vnam_templine)
                                     (mapcar 'vla-delete ls_vnam_templine)
                                     (setq ls_vnam_templine nil)
                                     ))

                               ))
                       (cons "STATUS"
                             (lambda()(mix_strasc;;現在のモード
                                       (if(= int_projectmode 6)
                                           (list "{\\C" str_gcol_y ";" 29694 22312 12398 12514 12540 12489 "}" )
                                         (list "{\\C" str_gcol_c ";" 12514 12540 12489 22793 26356  "}" )
                                         ))))
                       ;;\n名称、色の順で変更します(設定は任意です)
                       (cons "HELP"
                             (lambda()
                               (mix_strasc
                                (list 21517 31216 12289 33394 12398 38918 12391 22793 26356 12375 12414 12377
                                      "(" 35373 23450 12399 20219 24847 12391 12377 ")"
                                      ))))
                       )

                  (list(list 65);; 投影ピッチ
                       (cons "ITEM"(list 25237 24433 12500 12483 12481))
                       (cons "INPUT"(lambda()'pitch_project))
                       ;;選択した線形は、ここで設定したピッチで分割され、その点における標高を取得します\n元々の線形の節点に当たる部分は必ず投影されます\nピッチが0のとき節点のみが投影されます
                       (cons "HELP"(lambda()(mix_strasc(list 36984 25246 12375 12383 32218 24418 12399 12289 12371 12371 12391 35373 23450 12375 12383 12500 12483 12481 12391 20998 21106 12373 12428 12289 12381 12398 28857 12395 12362 12369 12427 27161 39640 12434 21462 24471 12375 12414 12377 "\n" 20803 12293 12398 32218 24418 12398 31680 28857 12395 24403 12383 12427 37096 20998 12399 24517 12378 25237 24433 12373 12428 12414 12377 "\n" 12500 12483 12481 12364 "0" 12398 12392 12365 31680 28857 12398 12415 12364 25237 24433 12373 12428 12414 12377(if int_selectmenu str_guide_inputval str_guide_selectval)  ))))
                       )

                  (list(list 82);;R節点円の半径
                       (cons "ITEM"(list 31680 28857 20870 12398 21322 24452 ) )
                       (cons "INPUT"(lambda()
                                      (if radius_node_temp T(setq radius_node_temp radius_node))
                                      'radius_node_temp))
                       ;;ピッチ設定しているとき投影時に節点数が増え、元々節点だった箇所がわかりづらくなるので、円形のマーキングを作ります
                       (cons "HELP"(lambda()(mix_strasc(list  12500 12483 12481 35373 23450 12375 12390 12356 12427 12392 12365 25237 24433 26178 12395 31680 28857 25968 12364 22679 12360 12289 20803 12293 31680 28857 12384 12387 12383 31623 25152 12364 12431 12363 12426 12389 12425 12367 12394 12427 12398 12391 12289 20870 24418 12398 12510 12540 12461 12531 12464 12434 20316 12426 12414 12377   ))))
                       )

                  (list(list 69);;E結合の許容値
                       (cons "ITEM"(list 32080 21512 12398 35377 23481 20516  ))
                       (cons "INPUT"(lambda()
                                      (if allow_joint T(setq allow_joint(* 0.01 pitch_project)))
                                      'allow_joint))
                       ;;選択した線が分離しているとき、端点間の距離がこの値よりも小さい場合結合します
                       (cons "HELP"(lambda()(mix_strasc(list 36984 25246 12375 12383 32218 12364 20998 38626 12375 12390 12356 12427 12392 12365 12289 31471 28857 38291 12398 36317 38626 12364 12371 12398 20516 12424 12426 12418 23567 12373 12356 22580 21512 32080 21512 12375 12414 12377 (if int_selectmenu str_guide_inputval str_guide_selectval)  ))))
                       )

                  (list(list 67);;クリック生成時に平面図作成
                       (cons "ITEM"(list 12463 12522 12483 12463 29983 25104 26178 12395
                                          24179 38754 22259 20316 25104 ))
                       (cons "LOADFUNCTION"(lambda()(setq bool_clickproject(null bool_clickproject))))
                       (cons "STATUS"
                             (lambda()
                               (mix_strasc
                                (if(vl-position int_projectmode(list 2 3))
                                    (if bool_clickproject
                                        (list "{\\C" str_gcol_g ";" 12377 12427 "}")
                                      (list "{\\C" str_gcol_y ";" 12375 12394 12356 "}"))
                                  (list "{\\C" str_gcol_p ";" 29694 22312 28961 21177 "}" )
                                  )
                                ) )
                             )
                       ;;クリック生成モードで地表面に線を作成したとき\n平面に投影した線形を同時に生成するかどうか選びます
                       (cons "HELP"
                             (lambda()
                               (mix_strasc(list 12463 12522 12483 12463 29983 25104 12514 12540 12489 12391 22320 34920 38754 12395 32218 12434 20316 25104 12375 12383 12392 12365 "\n" 24179 38754 12395 25237 24433 12375 12383 32218 24418 12434 21516 26178 12395 29983 25104 12377 12427 12363 12393 12358 12363 36984 12403 12414 12377 )))
                             )
                       )
                  
                  ;; (list(list 88);;X投影した線を選択したときの動作
                  ;;      (cons "ITEM"(list 25237 24433 12375 12383 32218 12434 36984 25246 12375 12383 12392 12365 12398 21205 20316 ))
                  ;;      (cons "INPUTSWITCH"
                  ;;            (lambda()
                  ;;              (list 'int_reproject
                  ;;                    (mapcar 'mix_strasc 
                  ;;                            (list(list "{\\C" str_gcol_c ";" 20877 25237 24433 "}")
                  ;;                                 (list "{\\C" str_gcol_y ";" 32080 21512 "}")))
                  ;;                    )))
                  ;;      ;;再投影:初回投影したときと異なる標高を使っていればその標高に投影しなおします\n標高が異なっていないときは同じ位置に複製されるだけです\n結合:選択した線の端点が一致しているとき線を結合します\n標高選択は関係ありません
                  ;;      (cons "HELP"(lambda()(mix_strasc(list 20877 25237 24433 " : " 21021 22238 25237 24433 12375 12383 12392 12365 12392 30064 12394 12427 27161 39640 12434 20351 12387 12390 12356 12428 12400 12381 12398 27161 39640 12395 25237 24433 12375 12394 12362 12375 12414 12377 "\n    " 27161 39640 12364 30064 12394 12387 12390 12356 12394 12356 12392 12365 12399 21516 12376 20301 32622 12395 35079 35069 12373 12428 12427 12384 12369 12391 12377  "\n" 32080 21512 " : " 36984 25246 12375 12383 32218 12398 31471 28857 12364 19968 33268 12375 12390 12356 12427 12392 12365 32218 12434 32080 21512 12375 12414 12377 "\n    " 27161 39640 36984 25246 12399 38306 20418 12354 12426 12414 12379 12435 ))))
                  ;;      )
                  
                  
                  (list(list 80);;選択モード切替
                       (cons "ITEM"(list 36984 25246 12514 12540 12489 20999 26367))
                       (cons "INPUTSWITCH"
                             (lambda()
                               (if(= int_selectmode -1)
                                   (list nil(mix_strasc
                                             (list "{\\C" str_gcol_p ";"
                                                   21336 20307 36984 25246 12398 12415 "}")))
                                 (list 'int_selectmode
                                       (mapcar 'mix_strasc
                                               (list(list "{\\C" str_gcol_y ";" 36984 25246 "}")
                                                    (list "{\\C" str_gcol_c ";" 35299 38500 "}")))
                                       ))))
                       (cons "HELP"(lambda()str_guide_selectmode))
                       )

                  
                  (list(list nil)
                       (cons "ITEM"(list ))
                       (cons "BOOL" (lambda() (if bool_point nil ls_vnam_select) ))
                       (cons
                        "STATUS"
                        (lambda( / bool_depth ii ls_out)
                          (if ls_vnam_select
                              (list
                               (list "{\\C" str_gcol_y ";" 36984 25246 12354 12426  " " 9733 "}")
                               ))
                          )
                        )
                       )
                  
                  (list(list "ENTER");;メインメニューへ
                       (cons "ITEM"(list 12513 12452 12531 12513 12491 12517 12540 12408))
                       (cons "NEXTMODE" "home"))
                  )
                 
                 ))
       
       (if(cadr bool)
           (progn
             (list ;;(list nil 'sym val)
              )
             ))
       ))

    ;;GUIDE,MOVE
    
    (cons
     "CLICK"
     (lambda()

       (cond
        ((if bool_point
             (if(setq p(car(project_to_ground
                            (list(if p_snap p_snap elem_grread))
                            (if(= int_projectmode 2)(list 0. 0. 1.)
                              (unit_vector(getvar "VIEWDIR")))
                            (list str_lasground height_ground)))
                      )
                 T
               ;;ここでは投影できません
               (x-alert(list 12371 12371 12391 12399 25237 24433 12391 12365 12414 12379 12435 ))
               ))
         
         (setq vnam
               (vla-addcircle
                (vla-get-modelspace(vla-get-activedocument(vlax-get-acad-object)))
                (vlax-3d-point p)radius_node_temp)
               vnam_point(car ls_vnam_projectcircle)
               ls_vnam_projectcircle(cons vnam ls_vnam_projectcircle)
               ls_vnam_select(cons vnam ls_vnam_select)
               )
         (addkillobj vnam)

         (if vnam_point
             (progn
               (setq vnam
                     (vla-addline
                      (vla-get-modelspace(vla-get-activedocument(vlax-get-acad-object)))
                      (vla-get-center vnam_point)(vlax-3d-point p))
                     ls_vnam_templine(cons vnam ls_vnam_templine) )
               (addkillobj vnam)
               ))

         
         
         
         )


        ((and(= int_projectmode 6)ls_vnam_select)
         ;; ((if(setq set_ent(ssget elem_grread(list(cons 0 "INSERT"))))
         ;;     (progn
         ;;       (setq vnam(vlax-ename->vla-object(ssname set_ent 0)))
         ;;       (exckillobj vnam)
         ;;       (vla-Highlight vnam :vlax-false)
         ;;       (setq ls_vnam_highlight(vl-remove vnam ls_vnam_highlight))
         ;;       (vla-getXData vnam "terraduct3d" 'array_Type 'array_Data )
         ;;       (if array_data
         ;;           (setq ls_xdata
         ;;                 (split_list 0(mapcar 'vlax-variant-value
         ;;                                      (vlax-safearray->list array_data)))
         ;;                 str_type(cdr(assoc "terraduct3d" ls_xdata)))
         ;;         (setq str_type nil) )
         ;;       (= str_type "PROJECT")))
         
         
         (setq str_bname(vla-get-name(car ls_vnam_select))
               str_origin str_bname)
         
         (settile_strinput
          'str_bname
          (lambda(str / bool)
            (if(or(= str str_origin)
                  (vl-catch-all-error-p
                   (vl-catch-all-apply 'vla-Item(list vnam_blocktable str)))
                  )
                T
              (if(= int_allow_overwrite 0)nil
                (progn
                  (alert
                   (mix_strasc(list 26082 12395 23384 22312 12377 12427 12502 12525 12483 12463 21517 31216 12391 12377 12364 19978 26360 12365 12373 12428 12414 12377 ))
                   )
                  T)))
            )
          
          (mix_strasc(list 21517 31216 22793 26356 ));;名称変更
          (mix_strasc(list 12502 12525 12483 12463 21517 31216 12364 26082 12395 23384 22312 12375 12390 12356 12414 12377 ))
          )

         (setq vnam(vl-catch-all-apply 'vla-Item(list vnam_blocktable str_origin)))
         (if(and(=(getvar "DIASTAT")1)(/= str_origin str_bname))
             (if(vl-catch-all-error-p vnam ) T (vla-put-name vnam str_bname)))

         (princ "");;なんか必要
         (if(setq i(acad_colordlg 1))
             (progn
               (vlax-for
                obj vnam
                (if(=(vla-get-ObjectName obj)"AcDb3dPolyline") (vla-put-color obj i)) )

               (vla-Regen(vla-get-ActiveDocument (vlax-get-acad-object))acAllViewports )
               
               ) )
         
         (setq bool_select nil p_selerac nil )

         
         
         )
        
        
        
        )
       
       ))
    
    (cons
     "KEYBOAD"
     (lambda( / ls_p bool_first ls_vnam block );;(d- gr2_home()
       (cond
        ((null(and(or(= elem_grread 13)(= int_grread 25))))
         )
        
        ((and(or(= int_projectmode 2)(= int_projectmode 3))
             ls_vnam_templine )
         
         (setq ls_p(mapcar '(lambda(a)(vlax-safearray->list(vlax-variant-value(vla-get-center a))))
                           (reverse ls_vnam_projectcircle))
               i 0)

         (if bool_clickproject
             (xvla-lwpoly(apply 'append(mapcar 'carxy ls_p))(list nil nil :vlax-false)))
         
         (mapcar '(lambda(vnam)
                    (setq ls_vnam_select(vl-remove vnam ls_vnam_select))
                    (exckillobj vnam)
                    (vla-delete vnam)
                    )
                 ls_vnam_projectcircle)
         (setq ls_vnam_projectcircle nil)
         (mapcar 'exckillobj ls_vnam_templine)
         (mapcar 'vla-delete ls_vnam_templine)
         (setq ls_vnam_templine nil)
         
         
         (while
             (progn
               (setq str_bname(strcat "FF" "ROAD$"(itoa(setq i(1+ i)))))
               (null
                (vl-catch-all-error-p
                 (vl-catch-all-apply 'vla-Item(list vnam_blocktable str_bname))))
               )
           )
         
         (setq block(vla-Add vnam_blockTable(vlax-3d-point 0 0 0)str_bname)
               ls_vla-release(cons block ls_vla-release))
         
         (setq bool_first T ls_int_node(list 0) int_node 0
               ls_p(apply 'append
                          (mapcar
                           '(lambda(p1 p2 / d n v ls_out ls_int)
                              (setq d(distance p1 p2)
                                    v(unit_vector(mapcar '- p2 p1))
                                    n(if(= pitch_project 0.)1
                                       (1+(fix(/ d pitch_project))))
                                    d(/ d n)
                                    )
                              (if bool_first
                                  (setq ls_int(inclist 0(1+ n))bool_first nil )
                                (setq ls_int(inclist 1(1+ n))))
                              
                              (setq int_node(+ int_node n)
                                    ls_int_node(cons int_node ls_int_node))
                              (mapcar '(lambda(i)(mapcar '(lambda(a b)(+ a(* i d b))) p1 v))
                                      ls_int)
                              )
                           ls_p(cdr ls_p)))
               
               ls_p(project_to_ground ls_p(list 0. 0. 1.)(list str_lasground height_ground))
               ;; ls_p(vl-remove nil ls_p)

               ;;radius_node(if(= radius_node 0.)0.05(* 0.2 pitch_project))
               )
           
         (if(= int_projectnode 1)nil
           (mapcar
            '(lambda(n / p v)
               (if(setq p(nth n ls_p))(setq v(vla-addcircle block (vlax-3d-point p)radius_node_temp)) ))
            ls_int_node))
         
         (setq ls_p(apply 'append ls_p) )
         (setq array_p(vlax-make-safearray vlax-vbDouble(cons 0 (1-(length ls_p)))))
         (vlax-safearray-fill array_p ls_p)
         
         (setq vnam(vla-Add3dPoly block array_p) )
         ;; (vla-put-color vnam int_col)
         
         (setq vnam(vla-InsertBlock
                    (vla-get-ModelSpace(vla-get-ActiveDocument(vlax-get-acad-object)))
                    (vlax-3d-point 0 0 0)str_bname 1 1 1 0)
               )
         
         (set_xda vnam(list(cons 1000 "PROJECT")
                           (cons 1000 "PROJECT")(cons 1000 str_hand))
                  "terraduct3d")
         
         
         (mapcar '(lambda(a)(vla-delete a))ls_vnam)
           
         ((lambda(v)
            (vlax-release-object v)
            (setq ls_vla-release(vl-remove v ls_vla-release)))
          block)
         
         
         
         )

        ((or(= elem_grread 13)(= int_grread 25))
         
         (mapcar '(lambda(v)
                    (if(if v(vl-position v ls_vnam_highlight))
                        (progn
                          (vla-Highlight v :vlax-false)
                          (setq ls_vnam_highlight(vl-remove v ls_vnam_highlight))
                          ))
                    )
                 ls_vnam_select)

         (setq ls_reunion_project(list))
         (setq ls_vnam_point
               (mapcar
                '(lambda(vnam)

                   (if(setq bool_reference(=(vla-get-objectname vnam)"AcDbBlockReference"))
                       (if(progn
                            (vla-getXData vnam "terraduct3d" 'array_Type 'array_Data )
                            (if array_data
                                (setq ls_xdata
                                      (split_list 0(mapcar 'vlax-variant-value
                                                           (vlax-safearray->list array_data)))
                                      str_type(cdr(assoc "terraduct3d" ls_xdata)))
                              (setq str_type nil) )
                            (= str_type "PROJECT")
                            )

                           (cond
                            ((= int_projectmode 4);;
                             (setq ls_p_center(list)ls_p_text(list))
                             (setq str(vla-get-name vnam))
                             
                             (if(setq num(vl-string-search "$" str))
                                 (setq str(substr str 1 num)))
                             (setq i 0)
                             (while
                                 (progn
                                   (setq str_bname(strcat str "ROAD$"(itoa(setq i(1+ i)))))
                                   (null
                                    (vl-catch-all-error-p
                                     (vl-catch-all-apply 'vla-Item(list vnam_blocktable str_bname))))
                                   )
                               )
                             (setq block(vla-Add vnam_blockTable(vlax-3d-point 0 0 0)str_bname)
                                   ls_vla-release(cons block ls_vla-release))
                             ;; ;; 含まれるすべてのオブジェクトを削除
                             ;; (vlax-for obj block(vla-delete obj))

                             (vlax-for
                              obj
                              (vla-Item vnam_blocktable(vla-get-name vnam))
                              (cond
                               ((=(vla-get-ObjectName obj)"AcDb3dPolyline")
                                (setq vnam_update obj
                                      ls_p(split_list 3(vlax-safearray->list(vlax-variant-value
                                                                             (vla-get-coordinates obj))))
                                      )
                                
                                )
                               ((=(vla-get-ObjectName obj)"AcDbCircle")
                                (setq p(vlax-safearray->list(vlax-variant-value(vla-get-center obj)))
                                      ls_p_center (cons p ls_p_center)
                                      )
                                
                                (setq p(car(project_to_ground
                                            (list p)(list 0. 0. 1.)(list str_lasground height_ground)))
                                      )
                                (vla-put-center obj(vlax-3d-point p))
                                
                                )
                               ((=(vla-get-ObjectName obj)"AcDbText")
                                (setq p(vlax-safearray->list(vlax-variant-value
                                                             (vla-get-TextAlignmentPoint obj)))
                                      p(car(project_to_ground
                                            (list p)(list 0. 0. 1.)(list str_lasground height_ground)))
                                      )
                                (vla-put-TextAlignmentPoint obj p)
                                
                                )
                               )
                              )

                             (setq ls_p
                                   (vl-remove-if
                                    '(lambda(p / bool)
                                       (setq ls_dummy ls_p_center bool T)
                                       (while ls_dummy
                                         (if(<(distance p(car ls_dummy))1e-8)
                                             (setq bool nil ls_dummy nil)
                                           (setq ls_dummy(cdr ls_dummy)))
                                         )
                                       bool)
                                    ls_p))
                             
                             (setq bool_first T ls_int_node(list 0) int_node 0
                                   ls_p(apply 'append
                                              (mapcar
                                               '(lambda(p1 p2 / d n v ls_out ls_int)
                                                  (setq d(distance p1 p2)
                                                        v(unit_vector(mapcar '- p2 p1))
                                                        n(if(= pitch_project 0.)1
                                                           (1+(fix(/ d pitch_project))))
                                                        d(/ d n)
                                                        )
                                                  (if bool_first
                                                      (setq ls_int(inclist 0(1+ n))bool_first nil )
                                                    (setq ls_int(inclist 1(1+ n))))
                                                  
                                                  (setq int_node(+ int_node n)
                                                        ls_int_node(cons int_node ls_int_node))
                                                  (mapcar '(lambda(i)(mapcar '(lambda(a b)(+ a(* i d b))) p1 v))
                                                          ls_int)
                                                  )
                                               ls_p(cdr ls_p)))
                                   
                                   ls_p(project_to_ground ls_p(list 0. 0. 1.)(list str_lasground height_ground))
                                   
                                   ls_p(apply 'append ls_p)
                                   )
                             
                             (setq array_p(vlax-make-safearray vlax-vbDouble(cons 0 (1-(length ls_p)))))
                             (vlax-safearray-fill array_p ls_p)
                             (vla-put-coordinates vnam_update array_p)
                             
                             
                             nil
                             )
                            
                            ((= int_projectmode 5);;

                             (setq ls_p_center(list)ls_p_text(list))
                             (vlax-for
                              obj
                              (vla-Item vnam_blocktable(vla-get-name vnam))
                              (cond
                               ((=(vla-get-ObjectName obj)"AcDb3dPolyline")
                                (setq ls_p(split_list 3(vlax-safearray->list(vlax-variant-value(vla-get-coordinates obj))))
                                      int_col(vla-get-color obj)
                                      )
                                )
                               ((=(vla-get-ObjectName obj)"AcDbCircle")
                                (setq p(vlax-safearray->list(vlax-variant-value(vla-get-center obj)))
                                      ls_p_center (cons p ls_p_center)
                                      )
                                )
                               
                               ((=(vla-get-ObjectName obj)"AcDbText")

                                (setq p(vlax-safearray->list(vlax-variant-value(vla-get-TextAlignmentPoint  obj)))
                                      ls_p_text(cons(list p(vla-get-rotation obj)) ls_p_text)
                                      )
                                
                                )
                               )
                              )
                             
                             (setq ls_reunion_project(cons(list vnam ls_p ls_p_center int_col ls_p_text)
                                                          ls_reunion_project))
                             nil
                             )
                            )
                         
                         )
                     (progn
                       
                       (setq ls_p(vl-catch-all-apply 'vla-get-coordinates(list vnam))
                             p0(vl-catch-all-apply 'vlax-curve-getstartpoint(list vnam))
                             p1(vl-catch-all-apply 'vlax-curve-getendpoint(list vnam))
                             int_col(get_visual_color vnam)
                             )
                       
                       (if(or(vl-catch-all-error-p p0) (vl-catch-all-error-p p1))
                           (progn
                             nil
                             )
                         (progn
                           (if(vl-catch-all-error-p ls_p)(setq ls_p(list p0 p1))
                             (setq ls_p(vlax-safearray->list(vlax-variant-value ls_p))
                                   ls_p(if(=(vla-get-ObjectName vnam)"AcDbPolyline")
                                           (progn
                                             (setq z(vla-get-elevation vnam))
                                             (mapcar '(lambda(a)(carxyz a z))(split_list 2 ls_p))
                                             )
                                         (split_list 3 ls_p))
                                   )
                             )
                           (setq ls_pa(mapcar
                                       '(lambda(p1 p2 / p p_c ag)
                                          (setq p(mapcar '(lambda(a b)(* 0.5(+ a b)))p1 p2)
                                                p_c(vlax-curve-getclosestpointto vnam p nil)
                                                
                                                
                                                )
                                          (if(<(distance p p_c)1e-8)nil
                                            
                                            ((lambda( / vec d)
                                               (setq vec(mapcar '- p2 p1)
                                                     vec(unit_vector
                                                         (list(-(cadr vec))(car vec)0))
                                                     d(apply '+(mapcar '*(mapcar '- p_c p)vec))
                                                     )
                                               (if(> d 0)
                                                   (setq ag(angle p1 p2)
                                                         p_c(mapcar '(lambda(a b)(+ a(* radius_node_temp b)))
                                                                    p vec)
                                                         )
                                                 (setq ag(angle p2 p1)
                                                       p_c(mapcar '(lambda(a b)(+ a(* radius_node_temp -1 b)))
                                                                  p vec)
                                                       )
                                                 )
                                               (list p_c ag)
                                               ))
                                            )
                                          )
                                       ls_p(cdr ls_p))
                                 ls_pa(vl-remove nil ls_pa)
                                 )
                           
                           (list vnam ls_p ls_pa)
                           ))
                       )
                     )
                   )
                ls_vnam_select)
               ls_vnam_point(vl-remove nil ls_vnam_point)
               )

         
         
         (setq ls_vnam_reunion(list))
         (while ls_reunion_project
           (setq lst(car ls_reunion_project)
                 vnam0(car lst)ls_p0(cadr lst)ls_pc0(caddr lst)int_col(cadddr lst)
                 ls_pa0(nth 4 lst)
                 p00(car ls_p0)p01(last ls_p0)
                 ls_reunion_project(cdr ls_reunion_project)
                 ls_dummy ls_reunion_project)
           (setq bool_reunion nil)
           (while
               ((lambda(ls_dummy2 / bool pe0 pe1 px)
                  (while ls_dummy2
                    (setq lst(car ls_dummy2)ls_dummy2(cdr ls_dummy2)
                          vnam1(car lst)ls_p1(cadr lst)ls_pc1(caddr lst)
                          ls_pa1(nth 4 lst)
                          p10(car ls_p1)p11(last ls_p1)
                          )

                    (if(cond
                        ((<(distance p00 p10)allow_joint)
                         (setq px(mapcar '(lambda(a b)(* 0.5(+ a b)))p00 p10)
                               ls_p0(append(reverse(cdr ls_p1))(list px)(cdr ls_p0))
                               ls_pa0(append ls_pa0 ls_pa1)
                               pe0 p00 pe1 p10 p00 p11 bool_reunion T bool T )
                         )
                        ((<(distance p00 p11)allow_joint)
                         (setq px(mapcar '(lambda(a b)(* 0.5(+ a b)))p00 p11)
                               ls_p0(append(subst px p11 ls_p1)(cdr ls_p0))
                               ls_pa0(append ls_pa0 ls_pa1)
                               pe0 p00 pe1 p11 p00 p10 bool_reunion T bool T )
                         )
                        ((<(distance p01 p10)allow_joint)
                         (setq px(mapcar '(lambda(a b)(* 0.5(+ a b)))p01 p10)
                               ls_p0(append(subst px p01 ls_p0)(cdr ls_p1))
                               ls_pa0(append ls_pa0 ls_pa1)
                               pe0 p01 pe1 p10 p01 p11 bool_reunion T bool T )
                         )
                        ((<(distance p01 p11)allow_joint)
                         (setq px(mapcar '(lambda(a b)(* 0.5(+ a b)))p01 p11)
                               ls_p0(append(subst px p01 ls_p0)(cdr(reverse ls_p1)))
                               ls_pa0(append ls_pa0 ls_pa1)
                               pe0 p01 pe1 p11 p01 p10 bool_reunion T bool T )
                         )
                        )
                        (progn
                          (setq ls_reunion_project(vl-remove lst ls_reunion_project)
                                ls_dummy(vl-remove lst ls_dummy)
                                ls_pc0(append(vl-remove-if '(lambda(p)(<(distance p pe0)1e-8))ls_pc0)
                                             (list px)
                                             (vl-remove-if '(lambda(p)(<(distance p pe1)1e-8))ls_pc1))
                                )
                          (vla-delete vnam1)
                          ))
                    )
                  bool)
                ls_dummy))
           
           (if bool_reunion
               (setq ls_vnam_reunion(cons(list vnam0 ls_p0 ls_pc0 int_col ls_pa0)ls_vnam_reunion)))
           
           )

         (while ls_vnam_reunion
           (setq lst(car ls_vnam_reunion)ls_vnam_reunion(cdr ls_vnam_reunion)
                 vnam(car lst)ls_p(cadr lst)ls_pc(caddr lst)int_col(cadddr lst)
                 ls_pa(nth 4 lst)
                 str(vla-get-name vnam)i 0)
           (vla-delete vnam)
           
           (if(setq num(vl-string-search "$" str))
               (setq str(substr str 1 num)))
           
           
           (while
               (progn
                 (setq str_bname(strcat str "$"(itoa(setq i(1+ i)))))
                 (null
                  (vl-catch-all-error-p
                   (vl-catch-all-apply 'vla-Item(list vnam_blocktable str_bname))))
                 )
             )

           (setq block(vla-Add vnam_blockTable(vlax-3d-point 0 0 0)str_bname)
                 ls_vla-release(cons block ls_vla-release))
           ;; ;; 含まれるすべてのオブジェクトを削除
           ;; (vlax-for obj block(vla-delete obj))
           (mapcar '(lambda(p)(vla-addcircle block(vlax-3d-point p)radius_node_temp))
                   ls_pc)
           
           (mapcar
            '(lambda(lst / p v vnam )
               (setq p(vlax-3d-point(car lst))
                     vnam(vla-addtext block "arc" p radius_node_temp))
               (vla-put-Alignment vnam 13)
               (vla-put-TextAlignmentPoint vnam p)
               )
            ls_pa)
           
           (setq ls_p(apply 'append ls_p) )
           (setq array_p(vlax-make-safearray vlax-vbDouble(cons 0 (1-(length ls_p)))))
           (vlax-safearray-fill array_p ls_p)

           (setq vnam(vla-Add3dPoly block array_p))
           (vla-put-color vnam int_col)
           (setq vnam(vla-InsertBlock
                      (vla-get-ModelSpace(vla-get-ActiveDocument(vlax-get-acad-object)))
                      (vlax-3d-point 0 0 0)str_bname 1 1 1 0)
                 )
           (set_xda vnam(list(cons 1000 "PROJECT")
                             (cons 1000 "PROJECT")(cons 1000 ""))
                    "terraduct3d")

           ((lambda(v)
              (vlax-release-object v)
              (setq ls_vla-release(vl-remove v ls_vla-release)))
            block)
           
           )

         
         (vla-Regen (vla-get-ActiveDocument (vlax-get-acad-object)) acAllViewports )
         
         (setq ls_dummy ls_vnam_point ls_vnam_select(list))

         (while ls_vnam_point
           (setq lst(car ls_vnam_point)
                 vnam0(car lst)ls_p0(cadr lst)ls_pa0(caddr lst)
                 p00(car ls_p0)p01(last ls_p0)
                 ls_vnam_point(cdr ls_vnam_point)
                 ls_dummy ls_vnam_point)

           (while
               ((lambda(ls_dummy2 / bool)
                  (while ls_dummy2
                    (setq lst(car ls_dummy2)ls_p1(cadr lst)ls_pa1(caddr lst)
                          ls_dummy2(cdr ls_dummy2)
                          p10(car ls_p1)p11(last ls_p1)
                          )
                    
                    (if(cond
                        ((<(distance p00 p10)allow_joint)
                         (setq px(mapcar '(lambda(a b)(* 0.5(+ a b)))p00 p10)
                               ls_p0(append(reverse(cdr ls_p1))(list px)(cdr ls_p0))
                               ls_pa0(append ls_pa0 ls_pa1)
                               p00 p11 bool_reunion T bool T )
                         )
                        ((<(distance p00 p11)allow_joint)
                         (setq px(mapcar '(lambda(a b)(* 0.5(+ a b)))p00 p11)
                               ls_p0(append(subst px p11 ls_p1)(cdr ls_p0))
                               ls_pa0(append ls_pa0 ls_pa1)
                               p00 p10 bool_reunion T bool T )
                         )
                        ((<(distance p01 p10)allow_joint)
                         (setq px(mapcar '(lambda(a b)(* 0.5(+ a b)))p01 p10)
                               ls_p0(append(subst px p01 ls_p0)(cdr ls_p1))
                               ls_pa0(append ls_pa0 ls_pa1)
                               p01 p11 bool_reunion T bool T )
                         )
                        ((<(distance p01 p11)allow_joint)
                         (setq px(mapcar '(lambda(a b)(* 0.5(+ a b)))p01 p11)
                               ls_p0(append(subst px p01 ls_p0)(cdr(reverse ls_p1)))
                               ls_pa0(append ls_pa0 ls_pa1)
                               p01 p10 bool_reunion T bool T )
                         )
                        )
                        (progn
                          (setq ls_vnam_point(vl-remove lst ls_vnam_point)
                                ls_dummy(vl-remove lst ls_dummy))
                          ))
                    )
                  bool)
                ls_dummy))
           
           (setq ls_vnam_select(cons(list vnam0 ls_p0 ls_pa0)ls_vnam_select))
           )
         
         (while ls_vnam_select
           (setq lst(car ls_vnam_select)ls_vnam_select(cdr ls_vnam_select)
                 vnam(car lst)ls_p(cadr lst)ls_pa(caddr lst)
                 str_hand(vla-get-handle vnam)i 0)
           
           (while
               (progn
                 (setq str_bname(strcat str_hand "ROAD$"(itoa(setq i(1+ i)))))
                 (null
                  (vl-catch-all-error-p
                   (vl-catch-all-apply 'vla-Item(list vnam_blocktable str_bname))))
                 )
             )
           
           (setq block(vla-Add vnam_blockTable(vlax-3d-point 0 0 0)str_bname)
                 ls_vla-release(cons block ls_vla-release))
           ;; 含まれるすべてのオブジェクトを削除
           ;; (vlax-for obj block(vla-delete obj))

           
           (setq bool_first T ls_int_node(list 0) int_node 0
                 ls_p(apply 'append
                            (mapcar
                             '(lambda(p1 p2 / d n v ls_out ls_int)
                                (setq d(distance p1 p2)
                                      v(unit_vector(mapcar '- p2 p1))
                                      n(if(= pitch_project 0.)1
                                         (1+(fix(/ d pitch_project))))
                                      d(/ d n)
                                      )
                                (if bool_first
                                    (setq ls_int(inclist 0(1+ n))bool_first nil )
                                  (setq ls_int(inclist 1(1+ n))))
                                
                                (setq int_node(+ int_node n)
                                      ls_int_node(cons int_node ls_int_node))
                                (mapcar '(lambda(i)(mapcar '(lambda(a b)(+ a(* i d b))) p1 v))
                                        ls_int)
                                )
                             ls_p(cdr ls_p)))
                 
                 ls_p(project_to_ground ls_p(list 0. 0. 1.)(list str_lasground height_ground))
                 ;; ls_p(vl-remove nil ls_p)

                 ;;radius_node(if(= radius_node 0.)0.05(* 0.2 pitch_project))
                 )
           
           (if(= int_projectnode 1)nil
             (mapcar
              '(lambda(n / p v)
                 (if(setq p(nth n ls_p))(setq v(vla-addcircle block (vlax-3d-point p)radius_node_temp)) ))
              ls_int_node))

           
           (setq ls_p(apply 'append ls_p) )
           (setq array_p(vlax-make-safearray vlax-vbDouble(cons 0 (1-(length ls_p)))))
           (vlax-safearray-fill array_p ls_p)

           (mapcar
            '(lambda(lst / p v vnam )
               (setq p(vlax-3d-point
                       (car(project_to_ground
                            (list(car lst))(list 0. 0. 1.)(list str_lasground height_ground)))
                       )
                     vnam(vla-addtext block "arc" p radius_node_temp))
               (vla-put-Alignment vnam 13)
               (vla-put-rotation vnam(cadr lst))
               (vla-put-TextAlignmentPoint vnam p)
               )
            ls_pa)
           
           
           (setq vnam(vla-Add3dPoly block array_p) )
           (vla-put-color vnam int_col)
           
           (setq vnam(vla-InsertBlock
                      (vla-get-ModelSpace(vla-get-ActiveDocument(vlax-get-acad-object)))
                      (vlax-3d-point 0 0 0)str_bname 1 1 1 0)
                 )
           
           (set_xda vnam(list(cons 1000 "PROJECT")
                             (cons 1000 "PROJECT")(cons 1000 str_hand))
                    "terraduct3d")
           
           
           (mapcar '(lambda(a)(vla-delete a))ls_vnam)
           
           ((lambda(v)
              (vlax-release-object v)
              (setq ls_vla-release(vl-remove v ls_vla-release)))
            block)
           
           )
         
         
         )
        )
       
       ))
    
    )

   (list
    "makeductmain" ;;edsym
    (cons
     "INITIAL"
     (lambda(bool);;initial
       (if(car bool)
           (progn
             (setq bool_point nil
                   bool_selectent nil bool_select nil int_selectmode -1
                   ls_ssget nil xtype_ssget nil xdata_ssget nil
                   ;;ls_ssgetを変えるときは注意
                   )
             
             (if(or(vl-position str_editreturn(list "insertarc" "tempdistlength"))
                   bool_tempdistlength )
                 (setq bool_tempdistlength nil)
               (setq vnam_road nil ls_vnam_duct(list) vnam_depth nil entna_depth nil
                     int_ductdepth nil
                     int_max_duct 0 int_min_duct 0
                     bool_ductedit nil bool_solidon nil
                     int_connecttype 0
                     vnam_currentinsert nil
                     int_selectmenu_ductedit nil int_adddepth nil
                     p_roadclick_temp nil
                     ls_p_dimtext nil
                     str_name_profile nil
                     int_bool_branch 0
                     )
               )
             
             (setq func_guidemenu
                   (lambda()
                     (mix_strasc
                      (list
                       (cond
                        
                        ((and(null str_lasground)(null height_ground))
                         ;;まず地表面標高を決定してください
                         (list 12414 12378 22320 34920 38754 27161 39640 12434 27770 23450 12375 12390 12367 12384 12373 12356))
                        (entna_depth
                         ;;既に作成済みの深度の位置を変更しています
                         (list 26082 12395 20316 25104 28168 12415 12398 28145 24230 12398 20301 32622 12434 22793 26356 12375 12390 12356 12414 12377 )
                         )
                        
                        ((= int_ductmode 0);;作成編集
                         (if(or ls_vnam_duct bool_ductedit)
                             (list
                              30452 32218 37096
                              ((lambda( / ii)
                                 (setq ii 0)
                                 (mapcar '(lambda(lst)
                                            (if(assoc "DEPTH" lst)(setq ii(1+ ii))))
                                         ls_vnam_duct)
                                 (if(=(rem ii 2)0) "< 1 > " "< 2 > ")
                                 ))
                              28857 30446 12434 36984 25246
                              "\n\n"
                              ;;編集項目
                              12304 32232 38598 38917 30446 12305 
                              "\n" 28145 24230 23544 27861 "(" 25991 23383 ");" 28145 12373 22793 26356
                              "\n" 28145 24230 23544 27861 "(" 25991 23383 20197 22806 ");" 20301 32622 22793 26356
                               ;;深さ寸法(文字);深さ変更,深さ寸法(文字以外);位置変更

                              "\n" 20870 24359 23544 27861 "(" 25991 23383 ");" 26354 12370 21322 24452
                              "\n" 20870 24359 23544 27861 "(" 25991 23383 20197 22806 ");"
                              20301 32622 22793 26356 "(" 21487 33021 12394 26178 12398 12415 ")" 
                              ;;円弧部;曲げ半径,
                              "\n" 30452 32218 37096 ";" 30452 32218 37096 12434 21066 38500
                              
                              )
                           
                           (list
                            (if(= int_allow_noroad_temp 1)
                                ;;任意点をクリックすると経路を使わず標高を指定できます
                                (list 20219 24847 28857 12434 12463 12522 12483 12463 12377 12427 12392 32076 36335 12434 20351 12431 12378 27161 39640 12434 25351 23450 12391 12365 12414 12377))
                            ;;線形オブジェクトを選択すると経路として設定します
                            "\n" 32218 24418 12458 12502 12472 12455 12463 12488 12434 36984 25246 12377 12427 12392 32076 36335 12392 12375 12390 35373 23450 12375 12414 12377
                            ;;作成済みの管路を選択して編集開始
                            "\n" 20316 25104 28168 12415 12398 31649 36335 12434 36984 25246
                            32232 38598 38283 22987
                            )
                           )
                         )
                        
                        ((= int_ductmode 1);;更新コピー
                         (list
                          ;;作成済みの管路をクリックすると実行
                          20316 25104 28168 12415 12398 31649 36335 12434 12463 12522 12483 12463 12377 12427 12392
                          (if(and(= depth_duct 0.)(= offset_duct 0.))
                              (list 26356 26032) (list 12467 12500 12540))
                          23455 34892
                          )
                         )
                        
                        ((= int_ductmode 2) ;;削除
                         (list
                          ;;削除対象を選択してください
                          ;;\n管路を対象に選択でき、その他のものは選択しようとしてもハイライトされません
                          ;;\n選択有り無し
                          ;;\n選択後Enterで削除
                          21066 38500 23550 35937 12434 36984 25246 12375 12390 12367 12384 12373 12356
                          "\n" 31649 36335 12434 23550 35937 12395 36984 25246 12391 12365 12289 12381 12398 20182 12398 12418 12398 12399 36984 25246 12375 12424 12358 12392 12375 12390 12418 12495 12452 12521 12452 12488 12373 12428 12414 12379 12435
                          "\n" 36984 25246 12304
                          (if ls_vnam_select(list 26377 12426)(list 28961 12375)) 12305
                          "\n" 36984 25246 24460 "Enter" 12391 21066 38500
                          )
                         )
                        );;cond
                       
                       )
                      )
                     )

                   int_commandpage 0 num_commandpage 2
                   
                   ls_exchangelevel nil
                   
                   ls_guideexplane
                   (mapcar
                    'mix_strasc
                    (list))
                   
                   )

             (setq 
              ls_guidemenu
              (list
               
               (list(list 73);;ぺージ切替
                    (cons "ITEM"(mix_strasc(list "{\\C" str_gcol_g ";" 12410 12540 12472 "}")))
                    (list "PAGE" 0 1)
                    (cons "LOADFUNCTION"
                          (lambda()
                            ;;旧: 画面上の断面登録(PAGE 2)中は切替不可としていた。
                            ;;PAGE 2 は DCL 化(td3dductsection)に伴い廃止
                            (setq int_commandpage(rem(1+ int_commandpage)num_commandpage))
                            ))
                    
                    (cons "STATUS"
                          (lambda()
                            (mix_strasc
                             (list "{\\C" str_gcol_y ";" (itoa(1+ int_commandpage)) "}"
                                   " / "
                                   "{\\C" str_gcol_c ";" (itoa num_commandpage) "}"))
                            )
                          )
                    (cons "HELP";;項目が多く、複数ページあります\n切り替えて使用してください
                          (lambda()
                            (mix_strasc(list 38917 30446 12364 22810 12367 12289 35079 25968 12506 12540 12472 12354 12426 12414 12377 "\n" 20999 12426 26367 12360 12390 20351 29992 12375 12390 12367 12384 12373 12356 ))))
                    )
               
               (list(list 76);; 地表面標高
                    (cons "ITEM"(mix_strasc(list 22320 34920 38754 27161 39640)))
                    (list "PAGE" 0)
                    (cons "STATUS"
                          (lambda()
                            (if str_lasground
                                (mix_strasc
                                 (list "{\\C" str_gcol_c ";" 12487 12540 12479 "} : "
                                       (vl-string-subst "" "lasgrid-" str_lasground)))
                              (if height_ground
                                  (mix_strasc
                                   (list"{\\C" str_gcol_g ";" 27161 39640 "} : "
                                        (as-numstr height_ground)))
                                (mix_strasc
                                 (list "{\\C" str_gcol_r ";"
                                       36984 25246 12373 12428 12390 12356 12414 12379 12435 "}"))
                                ))
                            ))
                    (cons "LOADFUNCTION"(lambda()(settile_selectground)))
                    ;;使用する標高を\n-las読込\n-xml読込\n-一定標高の数値入力\nから選択できます
                    (cons "HELP"(mix_strasc(list 20351 29992 12377 12427 27161 39640 12434 "\n- las" 35501 36796 "\n- xml" 35501 36796 "\n- " 19968 23450 27161 39640 12398 25968 20516 20837 21147 "\n" 12363 12425 36984 25246 12391 12365 12414 12377 )))
                    
                    )
               
               (list(list 67);;管の色
                    (cons "ITEM"(mix_strasc(list 31649 12398 33394)))
                    (list "PAGE" 0)
                    (cons "INPUTCOLOR"(lambda()
                                        (if int_colduct_temp T(setq int_colduct_temp int_colduct))
                                        'int_colduct_temp))
                    (cons "LOADFUNCTION"
                          (lambda()
                            (if ls_vnam_duct
                                (setq bool_replacegrread T int_grread 3 elem_grread(list 0 0 0)
                                      bool_noeditdepth T))
                            ))
                    ;;カラーダイアログが表示され、管のモデルに使う色を選択できます
                    (cons "HELP"(lambda()(mix_strasc(list 12459 12521 12540 12480 12452 12450 12525 12464 12364 34920 31034 12373 12428 12289 31649 12398 12514 12487 12523 12395 20351 12358 33394 12434 36984 25246 12391 12365 12414 12377 ))))
                    )
               
               (list(list 82) ;;R経路の曲げ半径,下限値
                    (cons "ITEM"(mix_strasc(list 32076 36335 12398 26354 12370 21322 24452
                                                 (if(= int_editarcradius 0)(list 19979 38480 20516))
                                                 )))
                    (list "PAGE" 0)
                    (cons "INPUT"(lambda()
                                   (if radius_bend_temp T(setq radius_bend_temp radius_bend))
                                   'radius_bend_temp))
                    ;;管路が曲線となる箇所における曲げ半径,の下限値\n曲げ半径は直線部の端点の位置から自動的に計算され、この値を下回ったとき、この値になる
                    (cons "HELP"
                          (lambda()
                            (mix_strasc
                             (list 31649 36335 12364 26354 32218 12392 12394 12427 31623 25152 12395 12362 12369 12427 26354 12370 21322 24452
                                   (if(= int_editarcradius 0)(list 12398 19979 38480 20516 "\n" 26354 12370 21322 24452 12399 30452 32218 37096 12398 31471 28857 12398 20301 32622 12363 12425 33258 21205 30340 12395 35336 31639 12373 12428 12289 12371 12398 20516 12434 19979 22238 12387 12383 12392 12365 12289 12371 12398 20516 12395 12394 12427 ))
                                   (if int_selectmenu str_guide_inputval str_guide_selectval)))))
                    )


               (list(list 71) ;;複数断面の設定
                    (cons "ITEM"(mix_strasc(list 35079 25968 26029 38754 12398 35373 23450  )))
                    (list "PAGE" 0)
                    (cons "STATUS"
                          (lambda()
                            (mix_strasc
                             (if str_name_profile
                                 (list str_name_profile)
                               (list 12394 12375 ))
                             )
                            )
                          )
                    (cons "LOADFUNCTION"
                          (lambda()
                            (td3dductsection)
                            (setq str_name_profile
                                  (if(vl-position str_ductsection td3d_ds_secnames)
                                      str_ductsection))
                            
                            ;; (setq int_commandpage 2
                            ;;       bool_setprofile T ls_vnam_select T
                            ;;       str_name_profile nil
                            ;;       ls_profile_display nil
                            ;;       num_profile 1
                            ;;       p_origin_profile nil
                            ;;       p_direction_profile nil
                            ;;       vec_x_profile(list 1. 0. 0.)
                            ;;       vec_y_profile(list 0. -1. 0.)
                            ;;       p_profile_center nil
                            ;;       )

                            ;; (setq ls_nameprofile
                            ;;       ((lambda(pattern / tbl name result nn)
                            ;;          (setq nn(1+(strlen pattern))
                            ;;                tbl (tblnext "BLOCK" T))  ; T で先頭から走査
                            ;;          (while tbl
                            ;;            (setq name (cdr (assoc 2 tbl)))
                            ;;            (if (wcmatch name(strcat pattern "*"))
                            ;;                (setq result (cons(substr name nn)result))
                            ;;              )
                            ;;            (setq tbl (tblnext "BLOCK"))
                            ;;            )
                            ;;          (reverse result)
                            ;;          )
                            ;;        "terraduct3d$")
                            ;;       )

                            ;; (if ls_nameprofile
                            ;;     (setq str_name_profile(car ls_nameprofile))
                            ;;   (progn
                            ;;     (setq str_name_profile "PROFILE$1"
                            ;;           ls_nameprofile(list str_name_profile)
                            ;;           )
                            ;;     ))
                            ;; (setq str_bname(strcat "terraduct3d$" str_name_profile) )
                            
                            ;; (if(vl-catch-all-error-p
                            ;;     (vl-catch-all-apply 'vla-Item(list vnam_blocktable str_bname)))
                            ;;     (setq block_profile(vla-Add vnam_blockTable(vlax-3d-point 0 0 0)str_bname))
                            ;;   (setq block_profile(vla-item vnam_blocktable str_bname))
                            ;;   )
                            
                            ;; (load_profile_block block_profile T)
                            
                            ))
                    ;;複数の断面を使って管路を作成する設定を開きます
                    (cons "HELP"
                          (lambda()
                            (mix_strasc(list 35079 25968 12398 26029 38754 12434 20351 12387 12390 31649 36335 12434 20316 25104 12377 12427 35373 23450 12434 38283 12365 12414 12377  )) )
                          )
                    )

               
               
               (list(list 84);;T保護コンクリートタイプ
                    (cons "ITEM"(mix_strasc(list 20445 35703 12467 12531 12463 12522 12540 12488 12479 12452 12503)))
                    (list "PAGE" 0)
                    (cons "INPUTSWITCH"
                          (lambda()
                            (if int_protectcon_temp T(setq int_protectcon_temp int_protectcon))
                            (list 'int_protectcon_temp
                                  (mapcar '(lambda(str c)(strcat "{\\C" c ";" str "}"))
                                          ls_type_protect
                                          (list str_gcol_g str_gcol_c str_gcol_p))
                                  )))
                    (cons "LOADFUNCTION"
                          (lambda()

                            (if ls_vnam_duct
                                (setq bool_replacegrread T int_grread 3 elem_grread(list 0 0 0)
                                      bool_noeditdepth T))
                            ))
                    ;;保護コンクリートの形状を「全周」、「下半のみ」、「なし」から選択します
                    ;;管の中心と同じ位置を中心とする長方形形状,「全周」の半分の高さの長方形\n※高さ入力値の考え方は全周と同じなので、入力値の半分の高さとなる
                    (cons "HELP"
                          (lambda()
                            
                            (setq ls_guide_drawing
                                  (list
                                   1
                                   
                                   (list(list -12.0 5.0 0.0)(list -2.0 5.0 0.0)3)
                                   (list(list -2.0 5.0 0.0)(list -2.0 -5.0 0.0)3)
                                   (list(list -2.0 -5.0 0.0)(list -12.0 -5.0 0.0)3)
                                   (list(list -12.0 -5.0 0.0)(list -12.0 5.0 0.0)3)
                                   (list(list -12.5 -5.0 0.0)(list -16.5 -5.0 0.0)30)
                                   (list(list -12.5 5.0 0.0)(list -16.5 5.0 0.0)30)
                                   (list(list -16.0 -4.0 0.0)(list -16.0 4.0 0.0)30)
                                   (list(list -15.7321 -4.0 0.0)(list -16.0 -5.0 0.0)30)
                                   (list(list -16.0 -5.0 0.0)(list -16.2679 -4.0 0.0)30)
                                   (list(list -16.0 -5.0 0.0)(list -16.0 -4.0 0.0)30)
                                   (list(list -16.2679 4.0 0.0)(list -16.0 5.0 0.0)30)
                                   (list(list -16.0 5.0 0.0)(list -15.7321 4.0 0.0)30)
                                   (list(list -16.0 5.0 0.0)(list -16.0 4.0 0.0)30)
                                   (list(list 17.0 0.0 0.0)(list 18.0 0.0 0.0)3)
                                   (list(list 18.0 0.0 0.0)(list 18.0 -5.0 0.0)3)
                                   (list(list 18.0 -5.0 0.0)(list 8.0 -5.0 0.0)3)
                                   (list(list 8.0 -5.0 0.0)(list 8.0 0.0 0.0)3)
                                   (list(list 8.0 0.0 0.0)(list 9.0 0.0 0.0)3)
                                   (list(list -3.0 0.0 0.0)(list -3.1363 1.03528 0.0)256)
                                   (list(list -3.1363 1.03528 0.0)(list -3.5359 2.0 0.0)256)
                                   (list(list -3.5359 2.0 0.0)(list -4.17157 2.82843 0.0)256)
                                   (list(list -4.17157 2.82843 0.0)(list -5.0 3.4641 0.0)256)
                                   (list(list -5.0 3.4641 0.0)(list -5.96472 3.8637 0.0)256)
                                   (list(list -5.96472 3.8637 0.0)(list -7.0 4.0 0.0)256)
                                   (list(list -7.0 4.0 0.0)(list -8.03528 3.8637 0.0)256)
                                   (list(list -8.03528 3.8637 0.0)(list -9.0 3.4641 0.0)256)
                                   (list(list -9.0 3.4641 0.0)(list -9.82843 2.82843 0.0)256)
                                   (list(list -9.82843 2.82843 0.0)(list -10.4641 2.0 0.0)256)
                                   (list(list -10.4641 2.0 0.0)(list -10.8637 1.03528 0.0)256)
                                   (list(list -10.8637 1.03528 0.0)(list -11.0 -1.2865e-15 0.0)256)
                                   (list(list -11.0 -1.2865e-15 0.0)(list -10.8637 -1.03528 0.0)256)
                                   (list(list -10.8637 -1.03528 0.0)(list -10.4641 -2.0 0.0)256)
                                   (list(list -10.4641 -2.0 0.0)(list -9.82843 -2.82843 0.0)256)
                                   (list(list -9.82843 -2.82843 0.0)(list -9.0 -3.4641 0.0)256)
                                   (list(list -9.0 -3.4641 0.0)(list -8.03528 -3.8637 0.0)256)
                                   (list(list -8.03528 -3.8637 0.0)(list -7.0 -4.0 0.0)256)
                                   (list(list -7.0 -4.0 0.0)(list -5.96472 -3.8637 0.0)256)
                                   (list(list -5.96472 -3.8637 0.0)(list -5.0 -3.4641 0.0)256)
                                   (list(list -5.0 -3.4641 0.0)(list -4.17157 -2.82843 0.0)256)
                                   (list(list -4.17157 -2.82843 0.0)(list -3.5359 -2.0 0.0)256)
                                   (list(list -3.5359 -2.0 0.0)(list -3.1363 -1.03528 0.0)256)
                                   (list(list -3.1363 -1.03528 0.0)(list -3.0 0.0 0.0)256)
                                   (list(list 17.0 0.0 0.0)(list 16.8637 1.03528 0.0)256)
                                   (list(list 16.8637 1.03528 0.0)(list 16.4641 2.0 0.0)256)
                                   (list(list 16.4641 2.0 0.0)(list 15.8284 2.82843 0.0)256)
                                   (list(list 15.8284 2.82843 0.0)(list 15.0 3.4641 0.0)256)
                                   (list(list 15.0 3.4641 0.0)(list 14.0353 3.8637 0.0)256)
                                   (list(list 14.0353 3.8637 0.0)(list 13.0 4.0 0.0)256)
                                   (list(list 13.0 4.0 0.0)(list 11.9647 3.8637 0.0)256)
                                   (list(list 11.9647 3.8637 0.0)(list 11.0 3.4641 0.0)256)
                                   (list(list 11.0 3.4641 0.0)(list 10.1716 2.82843 0.0)256)
                                   (list(list 10.1716 2.82843 0.0)(list 9.5359 2.0 0.0)256)
                                   (list(list 9.5359 2.0 0.0)(list 9.1363 1.03528 0.0)256)
                                   (list(list 9.1363 1.03528 0.0)(list 9.0 -1.2865e-15 0.0)256)
                                   (list(list 9.0 -1.2865e-15 0.0)(list 9.1363 -1.03528 0.0)256)
                                   (list(list 9.1363 -1.03528 0.0)(list 9.5359 -2.0 0.0)256)
                                   (list(list 9.5359 -2.0 0.0)(list 10.1716 -2.82843 0.0)256)
                                   (list(list 10.1716 -2.82843 0.0)(list 11.0 -3.4641 0.0)256)
                                   (list(list 11.0 -3.4641 0.0)(list 11.9647 -3.8637 0.0)256)
                                   (list(list 11.9647 -3.8637 0.0)(list 13.0 -4.0 0.0)256)
                                   (list(list 13.0 -4.0 0.0)(list 14.0353 -3.8637 0.0)256)
                                   (list(list 14.0353 -3.8637 0.0)(list 15.0 -3.4641 0.0)256)
                                   (list(list 15.0 -3.4641 0.0)(list 15.8284 -2.82843 0.0)256)
                                   (list(list 15.8284 -2.82843 0.0)(list 16.4641 -2.0 0.0)256)
                                   (list(list 16.4641 -2.0 0.0)(list 16.8637 -1.03528 0.0)256)
                                   (list(list 16.8637 -1.03528 0.0)(list 17.0 0.0 0.0)256)
                                   (list(list 7.5 -5.0 0.0)(list 3.5 -5.0 0.0)30)
                                   (list(list 7.5 5.0 0.0)(list 3.5 5.0 0.0)30)
                                   (list(list 4.0 -4.0 0.0)(list 4.0 4.0 0.0)30)
                                   (list(list 4.26795 -4.0 0.0)(list 4.0 -5.0 0.0)30)
                                   (list(list 4.0 -5.0 0.0)(list 3.73205 -4.0 0.0)30)
                                   (list(list 4.0 -5.0 0.0)(list 4.0 -4.0 0.0)30)
                                   (list(list 3.73205 4.0 0.0)(list 4.0 5.0 0.0)30)
                                   (list(list 4.0 5.0 0.0)(list 4.26795 4.0 0.0)30)
                                   (list(list 4.0 5.0 0.0)(list 4.0 4.0 0.0)30)
                                   (list(list -17.058 -0.499814 0.0)(list -17.058 0.501034 0.0)30)
                                   (list(list -16.3944 0.501034 0.0)(list -16.3944 -0.499814 0.0)30)
                                   (list(list -17.058 0.0244395 0.0)(list -16.3944 0.0244395 0.0)30)
                                   (list(list 2.92967 -0.499814 0.0)(list 2.92967 0.501034 0.0)30)
                                   (list(list 3.59691 0.501034 0.0)(list 3.59691 -0.499814 0.0)30)
                                   (list(list 2.92967 0.0244395 0.0)(list 3.59691 0.0244395 0.0)30)
                                   (list(list -8.41327 -7.66339 0.0)(list -8.41327 -8.99785 0.0)4)
                                   (list(list -9.41411 -7.66339 0.0)(list -7.41242 -7.66339 0.0)4)
                                   (list(list -9.24547 -8.28663 0.0)(list -7.58106 -8.28663 0.0)4)
                                   (list(list -9.57909 -8.99785 0.0)(list -7.24744 -8.99785 0.0)4)
                                   (list(list -7.91468 -6.96316 0.0)(list -7.24744 -7.49842 0.0)4)
                                   (list(list -8.41327 -6.49757 0.0)(list -7.91468 -6.96316 0.0)4)
                                   (list(list -8.91186 -6.96316 0.0)(list -8.41327 -6.49757 0.0)4)
                                   (list(list -9.57909 -7.49842 0.0)(list -8.91186 -6.96316 0.0)4)
                                   (list(list -5.91665 -8.66424 0.0)(list -5.91665 -8.16565 0.0)4)
                                   (list(list -4.74716 -8.66424 0.0)(list -5.91665 -8.66424 0.0)4)
                                   (list(list -4.74716 -8.16565 0.0)(list -4.74716 -8.66424 0.0)4)
                                   (list(list -5.91665 -8.16565 0.0)(list -4.74716 -8.16565 0.0)4)
                                   (list(list -5.9753 -7.1648 0.0)(list -4.6885 -7.1648 0.0)4)
                                   (list(list -6.08162 -7.66339 0.0)(list -4.58218 -7.66339 0.0)4)
                                   (list(list -5.33373 -6.83118 0.0)(list -5.33373 -7.66339 0.0)4)
                                   (list(list -4.41721 -8.99785 0.0)(list -4.41721 -6.66621 0.0)4)
                                   (list(list -4.74716 -8.99785 0.0)(list -4.41721 -8.99785 0.0)4)
                                   (list(list -6.48489 -8.84388 0.0)(list -6.58021 -8.99785 0.0)4)
                                   (list(list -6.34191 -8.53226 0.0)(list -6.48489 -8.84388 0.0)4)
                                   (list(list -6.2466 -7.90902 0.0)(list -6.34191 -8.53226 0.0)4)
                                   (list(list -6.2466 -6.66621 0.0)(list -6.2466 -7.90902 0.0)4)
                                   (list(list -6.2466 -6.66621 0.0)(list -4.41721 -6.66621 0.0)4)
                                   (list(list 11.9923 -7.49842 0.0)(list 12.4909 -7.99701 0.0)6)
                                   (list(list 11.3251 -7.1648 0.0)(list 11.9923 -7.49842 0.0)6)
                                   (list(list 11.3251 -6.49757 0.0)(list 11.3251 -8.99785 0.0)6)
                                   (list(list 10.3279 -6.49757 0.0)(list 12.6595 -6.49757 0.0)6)
                                   (list(list 13.6567 -6.66621 0.0)(list 13.9903 -6.99982 0.0)6)
                                   (list(list 13.9903 -6.99982 0.0)(list 14.159 -7.32977 0.0)6)
                                   (list(list 15.1561 -6.99982 0.0)(list 14.8225 -7.32977 0.0)6)
                                   (list(list 15.3248 -6.66621 0.0)(list 15.1561 -6.99982 0.0)6)
                                   (list(list 14.4926 -6.49757 0.0)(list 14.4926 -8.99785 0.0)6)
                                   (list(list 15.6584 -8.16565 0.0)(list 13.3268 -8.16565 0.0)6)
                                   (list(list 13.4917 -7.49842 0.0)(list 15.4898 -7.49842 0.0)6)
                                   
                                   )
                                  )
                            
                            (mix_strasc
                             (list 20445 35703 12467 12531 12463 12522 12540 12488 12398 24418 29366 12434
                                   "\n- " 20840 21608 ":" 31649 12398 20013 24515 12392 21516 12376 20301 32622 12434 20013 24515 12392 12377 12427 38263 26041 24418 24418 29366
                                   "\n- " 19979 21322 12398 12415 ":" "," 12300 20840 21608 12301 12398 21322 20998 12398 39640 12373 12398 38263 26041 24418 "\n  " 8251 39640 12373 20837 21147 20516 12398 32771 12360 26041 12399 20840 21608 12392 21516 12376 12394 12398 12391 12289 20837 21147 20516 12398 21322 20998 12398 39640 12373 12392 12394 12427
                                   "\n- " 12394 12375  "\n" 12363 12425 36984 25246 12375 12414 12377
                                   str_startguidedrawing
                                   
                                   ))))
                    )
               
               (list(list 68) ;;D.管直径
                    (cons "ITEM"(mix_strasc(list 31649 30452 24452)))
                    (list "PAGE" 0)
                    (cons "INPUT"(lambda()
                                   (if diam_duct_temp T(setq diam_duct_temp diam_duct))
                                   'diam_duct_temp))
                    (cons "LOADFUNCTION"
                          (lambda()
                            (if ls_vnam_duct
                                (setq bool_replacegrread T int_grread 3 elem_grread(list 0 0 0)
                                      bool_noeditdepth T))
                            ))
                    ;;管の直径を入力
                    (cons "HELP"(lambda( / p)
                                  (mix_strasc(list 31649 12398 30452 24452 12434 20837 21147 (if int_selectmenu str_guide_inputval str_guide_selectval) ))))
                    )
               
               (list(list 87) ;;w.保護コンクリート幅
                    (cons "ITEM"(mix_strasc(list 20445 35703 12467 12531 12463 12522 12540 12488 24133)))
                    (list "PAGE" 0)
                    (cons "INPUT"(lambda()
                                   (if width_protect_temp T(setq width_protect_temp width_protect))
                                   'width_protect_temp))
                    (cons "LOADFUNCTION"
                          (lambda()
                            (if ls_vnam_duct
                                (setq bool_replacegrread T int_grread 3 elem_grread(list 0 0 0)
                                      bool_noeditdepth T))
                            ))
                    ;;保護コンクリートの幅（水平方向）を入力
                    (cons "HELP"
                          (lambda()
                            (setq ls_guide_drawing
                                  (list
                                   1
                                   
                                   (list(list -5.5 3.0 0.0)(list -8.0 3.0 0.0)4)
                                   (list(list -7.5 6.25 0.0)(list -7.5 1.75 0.0)4)
                                   (list(list -3.0 5.5 0.0)(list -3.0 8.0 0.0)4)
                                   (list(list -6.25 7.5 0.0)(list -1.75 7.5 0.0)4)
                                   (list(list -3.5 5.0 0.0)(list -10.625 5.0 0.0)2)
                                   (list(list -3.5 -5.0 0.0)(list -10.625 -5.0 0.0)2)
                                   (list(list -10.0 5.0 0.0)(list -10.0 -5.0 0.0)2)
                                   (list(list -5.0 3.5 0.0)(list -5.0 10.625 0.0)6)
                                   (list(list 5.0 3.5 0.0)(list 5.0 10.625 0.0)6)
                                   (list(list -5.0 10.0 0.0)(list 5.0 10.0 0.0)6)
                                   (list(list -5.0 3.0 0.0)(list -3.0 5.0 0.0)3)
                                   (list(list -3.0 5.0 0.0)(list 3.0 5.0 0.0)3)
                                   (list(list 3.0 5.0 0.0)(list 5.0 3.0 0.0)3)
                                   (list(list 5.0 3.0 0.0)(list 5.0 -3.0 0.0)3)
                                   (list(list 5.0 -3.0 0.0)(list 3.0 -5.0 0.0)3)
                                   (list(list 3.0 -5.0 0.0)(list -3.0 -5.0 0.0)3)
                                   (list(list -3.0 -5.0 0.0)(list -5.0 -3.0 0.0)3)
                                   (list(list -5.0 -3.0 0.0)(list -5.0 3.0 0.0)3)
                                   (list(list 3.75 10.3349 0.0)(list 5.0 10.0 0.0)6)
                                   (list(list 5.0 10.0 0.0)(list 3.75 9.66512 0.0)6)
                                   (list(list -3.75 9.66512 0.0)(list -5.0 10.0 0.0)6)
                                   (list(list -5.0 10.0 0.0)(list -3.75 10.3349 0.0)6)
                                   (list(list -9.66512 -3.75 0.0)(list -10.0 -5.0 0.0)2)
                                   (list(list -10.0 -5.0 0.0)(list -10.3349 -3.75 0.0)2)
                                   (list(list -10.3349 3.75 0.0)(list -10.0 5.0 0.0)2)
                                   (list(list -10.0 5.0 0.0)(list -9.66512 3.75 0.0)2)
                                   (list(list -1.75 7.16512 0.0)(list -3.0 7.5 0.0)4)
                                   (list(list -3.0 7.5 0.0)(list -1.75 7.83488 0.0)4)
                                   (list(list -6.25 7.83488 0.0)(list -5.0 7.5 0.0)4)
                                   (list(list -5.0 7.5 0.0)(list -6.25 7.16512 0.0)4)
                                   (list(list -7.83488 1.75 0.0)(list -7.5 3.0 0.0)4)
                                   (list(list -7.5 3.0 0.0)(list -7.16513 1.75 0.0)4)
                                   (list(list -7.16513 6.25 0.0)(list -7.5 5.0 0.0)4)
                                   (list(list -7.5 5.0 0.0)(list -7.83488 6.25 0.0)4)
                                   (list(list -0.625 11.5625 0.0)(list -0.208333 10.3125 0.0)6)
                                   (list(list 0.208333 10.3125 0.0)(list 0.625 11.5625 0.0)6)
                                   (list(list -0.208333 10.3125 0.0)(list 0.0 10.9583 0.0)6)
                                   (list(list 0.0 10.9583 0.0)(list 0.208333 10.3125 0.0)6)
                                   (list(list -4.41667 7.8125 0.0)(list -4.41667 9.0625 0.0)4)
                                   (list(list -4.41667 9.0625 0.0)(list -3.58333 9.0625 0.0)4)
                                   (list(list -4.41667 8.4375 0.0)(list -3.97917 8.4375 0.0)4)
                                   (list(list -8.64583 3.375 0.0)(list -8.64583 4.625 0.0)4)
                                   (list(list -8.64583 4.625 0.0)(list -7.8125 4.625 0.0)4)
                                   (list(list -8.64583 4.0 0.0)(list -8.20833 4.0 0.0)4)
                                   (list(list -11.1458 -0.625 0.0)(list -11.1458 0.625 0.0)2)
                                   (list(list -10.3125 0.625 0.0)(list -10.3125 -0.625 0.0)2)
                                   (list(list -11.1458 0.0 0.0)(list -10.3125 0.0 0.0)2)
                                   ))
                            
                            (mix_strasc(list 20445 35703 12467 12531 12463 12522 12540 12488 12398 24133 65288 27700 24179 26041 21521 65289 12434 20837 21147(if int_selectmenu str_guide_inputval str_guide_selectval)
                                             str_startguidedrawing))))
                    )
               
               (list(list 72) ;;H.保護コンクリート高さ
                    (cons "ITEM"(mix_strasc(list 20445 35703 12467 12531 12463 12522 12540 12488 39640 12373)))
                    (list "PAGE" 0)
                    (cons "INPUT"(lambda()
                                   (if height_protect_temp T(setq height_protect_temp height_protect))
                                   'height_protect_temp))
                    (cons "LOADFUNCTION"
                          (lambda()
                            (if ls_vnam_duct
                                (setq bool_replacegrread T int_grread 3 elem_grread(list 0 0 0)
                                      bool_noeditdepth T))
                            ))
                    ;;保護コンクリートの高さ（鉛直方向）を入力
                    (cons "HELP"
                          (lambda()
                            (setq ls_guide_drawing
                                  (list
                                   1
                                   
                                   (list(list -5.5 3.0 0.0)(list -8.0 3.0 0.0)4)
                                   (list(list -7.5 6.25 0.0)(list -7.5 1.75 0.0)4)
                                   (list(list -3.0 5.5 0.0)(list -3.0 8.0 0.0)4)
                                   (list(list -6.25 7.5 0.0)(list -1.75 7.5 0.0)4)
                                   (list(list -3.5 5.0 0.0)(list -10.625 5.0 0.0)2)
                                   (list(list -3.5 -5.0 0.0)(list -10.625 -5.0 0.0)2)
                                   (list(list -10.0 5.0 0.0)(list -10.0 -5.0 0.0)2)
                                   (list(list -5.0 3.5 0.0)(list -5.0 10.625 0.0)6)
                                   (list(list 5.0 3.5 0.0)(list 5.0 10.625 0.0)6)
                                   (list(list -5.0 10.0 0.0)(list 5.0 10.0 0.0)6)
                                   (list(list -5.0 3.0 0.0)(list -3.0 5.0 0.0)3)
                                   (list(list -3.0 5.0 0.0)(list 3.0 5.0 0.0)3)
                                   (list(list 3.0 5.0 0.0)(list 5.0 3.0 0.0)3)
                                   (list(list 5.0 3.0 0.0)(list 5.0 -3.0 0.0)3)
                                   (list(list 5.0 -3.0 0.0)(list 3.0 -5.0 0.0)3)
                                   (list(list 3.0 -5.0 0.0)(list -3.0 -5.0 0.0)3)
                                   (list(list -3.0 -5.0 0.0)(list -5.0 -3.0 0.0)3)
                                   (list(list -5.0 -3.0 0.0)(list -5.0 3.0 0.0)3)
                                   (list(list 3.75 10.3349 0.0)(list 5.0 10.0 0.0)6)
                                   (list(list 5.0 10.0 0.0)(list 3.75 9.66512 0.0)6)
                                   (list(list -3.75 9.66512 0.0)(list -5.0 10.0 0.0)6)
                                   (list(list -5.0 10.0 0.0)(list -3.75 10.3349 0.0)6)
                                   (list(list -9.66512 -3.75 0.0)(list -10.0 -5.0 0.0)2)
                                   (list(list -10.0 -5.0 0.0)(list -10.3349 -3.75 0.0)2)
                                   (list(list -10.3349 3.75 0.0)(list -10.0 5.0 0.0)2)
                                   (list(list -10.0 5.0 0.0)(list -9.66512 3.75 0.0)2)
                                   (list(list -1.75 7.16512 0.0)(list -3.0 7.5 0.0)4)
                                   (list(list -3.0 7.5 0.0)(list -1.75 7.83488 0.0)4)
                                   (list(list -6.25 7.83488 0.0)(list -5.0 7.5 0.0)4)
                                   (list(list -5.0 7.5 0.0)(list -6.25 7.16512 0.0)4)
                                   (list(list -7.83488 1.75 0.0)(list -7.5 3.0 0.0)4)
                                   (list(list -7.5 3.0 0.0)(list -7.16513 1.75 0.0)4)
                                   (list(list -7.16513 6.25 0.0)(list -7.5 5.0 0.0)4)
                                   (list(list -7.5 5.0 0.0)(list -7.83488 6.25 0.0)4)
                                   (list(list -0.625 11.5625 0.0)(list -0.208333 10.3125 0.0)6)
                                   (list(list 0.208333 10.3125 0.0)(list 0.625 11.5625 0.0)6)
                                   (list(list -0.208333 10.3125 0.0)(list 0.0 10.9583 0.0)6)
                                   (list(list 0.0 10.9583 0.0)(list 0.208333 10.3125 0.0)6)
                                   (list(list -4.41667 7.8125 0.0)(list -4.41667 9.0625 0.0)4)
                                   (list(list -4.41667 9.0625 0.0)(list -3.58333 9.0625 0.0)4)
                                   (list(list -4.41667 8.4375 0.0)(list -3.97917 8.4375 0.0)4)
                                   (list(list -8.64583 3.375 0.0)(list -8.64583 4.625 0.0)4)
                                   (list(list -8.64583 4.625 0.0)(list -7.8125 4.625 0.0)4)
                                   (list(list -8.64583 4.0 0.0)(list -8.20833 4.0 0.0)4)
                                   (list(list -11.1458 -0.625 0.0)(list -11.1458 0.625 0.0)2)
                                   (list(list -10.3125 0.625 0.0)(list -10.3125 -0.625 0.0)2)
                                   (list(list -11.1458 0.0 0.0)(list -10.3125 0.0 0.0)2)
                                   ))
                            
                            (mix_strasc(list 20445 35703 12467 12531 12463 12522 12540 12488 12398 39640 12373 65288 37467 30452 26041 21521 65289 12434 20837 21147
                                             (if int_selectmenu str_guide_inputval str_guide_selectval)
                                             str_startguidedrawing
                                             
                                             ))))
                    )
               
               (list(list 70) ;;F.保護コンクリート面取り
                    (cons "ITEM"(mix_strasc(list 20445 35703 12467 12531 12463 12522 12540 12488 38754 21462 12426)))
                    (list "PAGE" 0)
                    (cons "INPUT"(lambda()
                                   (if filet_protect_temp T(setq filet_protect_temp filet_protect))
                                   'filet_protect_temp))
                    (cons "LOADFUNCTION"
                          (lambda()
                            (if ls_vnam_duct
                                (setq bool_replacegrread T int_grread 3 elem_grread(list 0 0 0)
                                      bool_noeditdepth T))
                            ))
                    ;;保護コンクリートの面取り（直角二等辺三角形で切り取られるので等辺の長さ）を入力\n0のとき面取りを行いません
                    (cons "HELP"
                          (lambda()
                            (setq ls_guide_drawing
                                  (list
                                   1
                                   
                                   (list(list -5.5 3.0 0.0)(list -8.0 3.0 0.0)4)
                                   (list(list -7.5 6.25 0.0)(list -7.5 1.75 0.0)4)
                                   (list(list -3.0 5.5 0.0)(list -3.0 8.0 0.0)4)
                                   (list(list -6.25 7.5 0.0)(list -1.75 7.5 0.0)4)
                                   (list(list -3.5 5.0 0.0)(list -10.625 5.0 0.0)2)
                                   (list(list -3.5 -5.0 0.0)(list -10.625 -5.0 0.0)2)
                                   (list(list -10.0 5.0 0.0)(list -10.0 -5.0 0.0)2)
                                   (list(list -5.0 3.5 0.0)(list -5.0 10.625 0.0)6)
                                   (list(list 5.0 3.5 0.0)(list 5.0 10.625 0.0)6)
                                   (list(list -5.0 10.0 0.0)(list 5.0 10.0 0.0)6)
                                   (list(list -5.0 3.0 0.0)(list -3.0 5.0 0.0)3)
                                   (list(list -3.0 5.0 0.0)(list 3.0 5.0 0.0)3)
                                   (list(list 3.0 5.0 0.0)(list 5.0 3.0 0.0)3)
                                   (list(list 5.0 3.0 0.0)(list 5.0 -3.0 0.0)3)
                                   (list(list 5.0 -3.0 0.0)(list 3.0 -5.0 0.0)3)
                                   (list(list 3.0 -5.0 0.0)(list -3.0 -5.0 0.0)3)
                                   (list(list -3.0 -5.0 0.0)(list -5.0 -3.0 0.0)3)
                                   (list(list -5.0 -3.0 0.0)(list -5.0 3.0 0.0)3)
                                   (list(list 3.75 10.3349 0.0)(list 5.0 10.0 0.0)6)
                                   (list(list 5.0 10.0 0.0)(list 3.75 9.66512 0.0)6)
                                   (list(list -3.75 9.66512 0.0)(list -5.0 10.0 0.0)6)
                                   (list(list -5.0 10.0 0.0)(list -3.75 10.3349 0.0)6)
                                   (list(list -9.66512 -3.75 0.0)(list -10.0 -5.0 0.0)2)
                                   (list(list -10.0 -5.0 0.0)(list -10.3349 -3.75 0.0)2)
                                   (list(list -10.3349 3.75 0.0)(list -10.0 5.0 0.0)2)
                                   (list(list -10.0 5.0 0.0)(list -9.66512 3.75 0.0)2)
                                   (list(list -1.75 7.16512 0.0)(list -3.0 7.5 0.0)4)
                                   (list(list -3.0 7.5 0.0)(list -1.75 7.83488 0.0)4)
                                   (list(list -6.25 7.83488 0.0)(list -5.0 7.5 0.0)4)
                                   (list(list -5.0 7.5 0.0)(list -6.25 7.16512 0.0)4)
                                   (list(list -7.83488 1.75 0.0)(list -7.5 3.0 0.0)4)
                                   (list(list -7.5 3.0 0.0)(list -7.16513 1.75 0.0)4)
                                   (list(list -7.16513 6.25 0.0)(list -7.5 5.0 0.0)4)
                                   (list(list -7.5 5.0 0.0)(list -7.83488 6.25 0.0)4)
                                   (list(list -0.625 11.5625 0.0)(list -0.208333 10.3125 0.0)6)
                                   (list(list 0.208333 10.3125 0.0)(list 0.625 11.5625 0.0)6)
                                   (list(list -0.208333 10.3125 0.0)(list 0.0 10.9583 0.0)6)
                                   (list(list 0.0 10.9583 0.0)(list 0.208333 10.3125 0.0)6)
                                   (list(list -4.41667 7.8125 0.0)(list -4.41667 9.0625 0.0)4)
                                   (list(list -4.41667 9.0625 0.0)(list -3.58333 9.0625 0.0)4)
                                   (list(list -4.41667 8.4375 0.0)(list -3.97917 8.4375 0.0)4)
                                   (list(list -8.64583 3.375 0.0)(list -8.64583 4.625 0.0)4)
                                   (list(list -8.64583 4.625 0.0)(list -7.8125 4.625 0.0)4)
                                   (list(list -8.64583 4.0 0.0)(list -8.20833 4.0 0.0)4)
                                   (list(list -11.1458 -0.625 0.0)(list -11.1458 0.625 0.0)2)
                                   (list(list -10.3125 0.625 0.0)(list -10.3125 -0.625 0.0)2)
                                   (list(list -11.1458 0.0 0.0)(list -10.3125 0.0 0.0)2)
                                   ))
                            
                            (mix_strasc(list  20445 35703 12467 12531 12463 12522 12540 12488 12398 38754 21462 12426 65288 30452 35282 20108 31561 36794 19977 35282 24418 12391 20999 12426 21462 12425 12428 12427 12398 12391 31561 36794 12398 38263 12373 65289 12434 20837 21147 "\n0" 12398 12392 12365 38754 21462 12426 12434 34892 12356 12414 12379 12435
                                              (if int_selectmenu str_guide_inputval str_guide_selectval)
                                              str_startguidedrawing
                                              ))))
                    )
               
               
               (list(list 90);;Zキャンセル項目を選択
                    (cons "ITEM"(mix_strasc(list 12461 12515 12531 12475 12523 38917 30446 12434 36984 25246 )))
                    (list "PAGE" 1)
                    (cons "INPUTSWITCH"(lambda()(list 'int_cancelduct ls_switch_cancelduct)))
                    (cons "NOREFERENCE"
                          (setq ls_switch_cancelduct
                                (mapcar 'mix_strasc;;直前の高度入力,経路の選択,管路の編集
                                        (list(list "{\\C" str_gcol_g ";"
                                                   30452 21069 12398 28145 24230 20837 21147 "}")
                                             (list "{\\C" str_gcol_c ";"
                                                   32076 36335 12398 36984 25246 "}")
                                             (list "{\\C" str_gcol_p ";"
                                                   31649 36335 12398 32232 38598 "}")
                                             )
                                        )
                                ))
                    ;;BackSpaceを押したときに実行する内容を選びます\n直前の高度入力：管中心位置の入力のうち、最後に作成したものを削除します\n経路の選択：現在選択されている経路の選択を解除します（他の経路を選択したいときなどに使用）\n管路の編集：管路編集をキャンセルし、編集前の状態に戻します
                    (cons "HELP"(lambda()(mix_strasc(list "BackSpace" 12434 25276 12375 12383 12392 12365 12395 23455 34892 12377 12427 20869 23481 12434 36984 12403 12414 12377 "\n" 30452 21069 12398 39640 24230 20837 21147 65306 31649 20013 24515 20301 32622 12398 20837 21147 12398 12358 12385 12289 26368 24460 12395 20316 25104 12375 12383 12418 12398 12434 21066 38500 12375 12414 12377 "\n" 32076 36335 12398 36984 25246 65306 29694 22312 36984 25246 12373 12428 12390 12356 12427 32076 36335 12398 36984 25246 12434 35299 38500 12375 12414 12377 65288 20182 12398 32076 36335 12434 36984 25246 12375 12383 12356 12392 12365 12394 12393 12395 20351 29992 65289 "\n" 31649 36335 12398 32232 38598 65306 31649 36335 32232 38598 12434 12461 12515 12531 12475 12523 12375 12289 32232 38598 21069 12398 29366 24907 12395 25147 12375 12414 12377 ))))
                    )
               
               (list(list 8);;キャンセルの実行
                    (cons "ITEM"(mix_strasc(list 12461 12515 12531 12475 12523 12398 23455 34892)))
                    (list "PAGE" 1)
                    (cons "LOADFUNCTION"
                          (lambda( / bool x)
                            
                            (cond
                             ((and(/= int_min_duct int_max_duct)(= int_cancelduct 0))
                              (setq bool T)
                              (while(and ls_vnam_duct bool)
                                (setq x(car ls_vnam_duct)
                                      ls_vnam_duct(cdr ls_vnam_duct))
                                (if(assoc "DEPTH" x)(setq bool nil))
                                (mapcar
                                 '(lambda(vnam)
                                    (if(=(type vnam)'VLA-OBJECT)
                                        (progn
                                          (vla-delete vnam)
                                          (exckillobj vnam)
                                          ))
                                    )
                                 (cdr(assoc "OBJ" x)))
                                )
                              ;;ls_vnam_ductの整理todo
                              (setq ii(1- int_min_duct))
                              (while(null(assoc(list "LINE"(setq ii(1+ ii)))ls_vnam_duct)))
                              (setq int_min_duct ii ii(1- ii)num_subtract 0)
                              (while(<=(setq ii(1+ ii))int_max_duct)
                                (if(assoc(list "LINE" ii)ls_vnam_duct)
                                    (if(= num_subtract 0)T
                                      (mapcar
                                       '(lambda(lst / str i j ls_subst ls_prev)
                                          (setq str(car lst)i(cadr lst)j(+ ii num_subtract)
                                                ls_prev(if i(list str ii i)(list str ii))
                                                ls_subst(if i(list str j i)(list str j)))
                                          (if(setq lst(assoc ls_prev ls_vnam_duct))
                                              (setq ls_vnam_duct
                                                    (subst(subst ls_subst ls_prev lst)
                                                          lst ls_vnam_duct)
                                                    )
                                            )
                                          )
                                       (list(list "LINE")(list "DEPTH" 0)(list "DEPTH" 1)
                                            (list "ARC" 0)(list "ARC" 1)))
                                      )
                                  (setq num_subtract(1- num_subtract)))
                                )
                              (setq int_max_duct(+ int_max_duct num_subtract))
                              
                              (setq bool_replacegrread T
                                    int_grread 3 elem_grread(list 0 0 0)
                                    bool_noeditdepth T)

                              (setq int_selectmenu_ductedit
                                    (if(= int_editdepth 0)
                                        (func_selectmenu_ductedit_depth ls_guidemenu_page)
                                      (if(= int_editdepth 1)
                                          (func_selectmenu_ductedit_offset ls_guidemenu_page))))
                              
                              )
                             
                             ((= int_cancelduct 1)
                              (if vnam_road
                                  (progn
                                    (setq str(mix_strasc
                                              (list 32076 36335 12398 36984 25246 12434 35299 38500 12375 12414 12375 12383));;経路の選択を解除しました
                                          )
                                    (if(vl-position vnam_road ls_vnam_killobj)
                                        (progn
                                          (vla-delete vnam_road)
                                          (exckillobj vnam)
                                          ))
                                    (setq vnam_road nil
                                          int_ductdepth nil)
                                    
                                    )
                                (setq str(mix_strasc(list 32076 36335 12364 12394 12356 12398 12391 35299 38500 12375 12414 12379 12435  )));;経路がないので解除しません
                                )
                              (princ str)
                              )
                             
                             ((= int_cancelduct 2)

                              (if bool_ductedit
                                  (progn
                                    (setq str(mix_strasc(list 31649 36335 32232 38598 12434 32066 20102 12375 12414 12375 12383) );;管路編集を終了しました
                                          bool_ductedit nil
                                          )
                                    
                                    (mapcar
                                     '(lambda(lst)
                                        (if(setq lst(assoc "OBJ" lst))
                                            (mapcar
                                             '(lambda(vnam)
                                                (if(=(type vnam)'VLA-OBJECT)
                                                    (progn
                                                      
                                                      (vla-delete vnam)
                                                      (exckillobj vnam)
                                                      ))
                                                )
                                             (cdr lst)))
                                        )
                                     ls_vnam_duct)
                                    (setq ls_vnam_duct nil)
                                    (if vnam_currentinsert
                                        (progn
                                          (vla-put-visible vnam_currentinsert :vlax-true)
                                          (setq ls_vnam_visible
                                                (vl-remove vnam_currentinsert ls_vnam_visible)
                                                vnam_currentinsert nil)
                                          ))
                                    
                                    (x-alert(list str))
                                    
                                    )
                                
                                )
                              )
                             )
                            
                            )
                          )
                    (cons "HELP"(lambda()"no guide"))
                    
                    )


               (list(list 49);;高度入力方法
                    (cons "ITEM"(mix_strasc(list 28145 24230 20837 21147 26041 27861 )))
                    (list "PAGE" 0 1)
                    (cons "INPUTSWITCH"
                          (lambda()
                            (if int_inputdepth_temp T(setq int_inputdepth_temp int_inputdepth))
                            (if(and(= int_ductmode 2)(= int_inputdepth_temp 2))(setq int_inputdepth_temp 1))
                            (list 'int_inputdepth_temp
                                  (mapcar '(lambda(str c)(strcat "{\\C" c ";" str "}"))
                                          ls_type_inputdepth
                                          (if(= int_ductmode 2)
                                              (list str_gcol_y str_gcol_c)
                                            (list str_gcol_y str_gcol_c str_gcol_g)))
                                  )))
                    ;;現在の標高データからの距離または標高値自体を入力するかを選択します\n標高データからの距離を入力するとき、上を正とするか下を正とするかを選択できます
                    (cons "HELP"(lambda()(mix_strasc(list 29694 22312 12398 27161 39640 12487 12540 12479 12363 12425 12398 36317 38626 12414 12383 12399 27161 39640 20516 33258 20307 12434 20837 21147 12377 12427 12363 12434 36984 25246 12375 12414 12377 "\n" 27161 39640 12487 12540 12479 12363 12425 12398 36317 38626 12434 20837 21147 12377 12427 12392 12365 12289 19978 12434 27491 12392 12377 12427 12363 19979 12434 27491 12392 12377 12427 12363 12434 36984 25246 12391 12365 12414 12377 ))))
                    )
               
               (list(list 50);;
                    (cons "ITEM"(mix_strasc(list 28145 24230) ))
                    (list "PAGE" 0 1)
                    (cons "INPUT"(lambda()
                                   (if depth_duct T(setq depth_duct 0.))
                                   'depth_duct))
                    (cons "KEYSEARCH" "DEPTH")
                    (cons "LOADFUNCTION"
                          (lambda()

                            ;; (if(and(= int_ductdepth 1)entna_depth)
                            ;;     (setq p_depth nil
                                      
                                      
                            ;;           entna_depth
                            ;;           (make_2pdimension
                            ;;            entna_depth(list p_road p_depth vec_normal dist_normal
                            ;;                             nil(* 0.5 pi) 0. str_level str_dimstyle_ductlevel))
                                      
                            ;;           )
                            ;;   )
                            nil
                            ))
                    ;;深度標高を入力\n入力方法の違いについては1行上で確認してください
                    (cons "HELP"(lambda()(mix_strasc(list 28145 24230 27161 39640 12434 20837 21147  "\n" 20837 21147 26041 27861 12398 36949 12356 12395 12388 12356 12390 12399 "1" 34892 19978 12391 30906 35469 12375 12390 12367 12384 12373 12356 (if int_selectmenu str_guide_inputval str_guide_selectval)
))))
                    )

               (list(list 51);;経路に対する水平オフセット
                    (cons "ITEM"(mix_strasc
                                 (list 32076 36335 12395 23550 12377 12427 27700 24179 12458 12501 12475 12483 12488
                                       "(" 21521 12363 12387 12390 21491 12364 27491 ")"
                                       ;;向かって右が正
                                       )))
                    (list "PAGE" 0 1)
                    (cons "INPUT"(lambda()(if offset_duct T(setq offset_duct 0.))'offset_duct))
                    (cons "KEYSEARCH" "OFFSET")
                    ;;水平オフセットを入力
                    (cons "HELP"(lambda()(mix_strasc(list 27700 24179 12458 12501 12475 12483 12488 12434 20837 21147(if int_selectmenu str_guide_inputval str_guide_selectval) ))))
                    
                    )

               (list(list 66);;他の管の中心を通る
                    (cons "ITEM"(list 20182 12398 31649 12398 20013 24515 12434 36890 12427  ))
                    (list "PAGE" 0)
                    (cons "INPUTSWITCH"
                          (lambda()
                            (list 'int_bool_branch;;無効\n管を選択してください
                                  (mapcar 'mix_strasc
                                          (list(list "{\\C" str_gcol_gy ";" 28961 21177 "}" )
                                               (list "{\\C" str_gcol_y ";" 31649 12434 36984 25246 12375 12390 12367 12384 12373 12356  "}" )))
                                  )))
                    (cons "LOADFUNCTION"
                          (lambda()
                            (if(and(= int_bool_branch 1)(null vnam_road))
                                (progn;;経路が選択されていないとき使用できません
                                  (x-alert(list 32076 36335 12364 36984 25246 12373 12428 12390 12356 12394 12356 12392 12365 20351 29992 12391 12365 12414 12379 12435 ))
                                  (setq int_bool_branch 0)
                                  ))
                            )
                          )
                    
                    ;;引込管の作成を想定し、他の管を選択するとその中心を通ることができます\n経路が必須です
                    (cons "HELP"(lambda()(mix_strasc(list 24341 36796 31649 12398 20316 25104 12434 24819 23450 12375 12289 20182 12398 31649 12434 36984 25246 12377 12427 12392 12381 12398 20013 24515 12434 36890 12427 12371 12392 12364 12391 12365 12414 12377 "\n" 32076 36335 12364 24517 38920 12391 12377  ))))
                    
                    )
               
               

               (list(list 52);;次に作成する箇所の追加方向
                    (cons "ITEM"(mix_strasc(list 27425 12395 20316 25104 12377 12427 31623 25152 12398 36861 21152 26041 21521 )))
                    (list "PAGE" 0 1)
                    (cons "INPUTSWITCH"
                          (lambda()
                            (if int_connecttype T(setq int_connecttype 0))
                            (list 'int_connecttype ls_switch_connecttype)))
                    (cons "NOREFERENCE"
                          (setq ls_switch_connecttype
                                (mapcar 'mix_strasc
                                        (list(list "{\\C" str_gcol_c ";"
                                                   32066 28857 20596 12395 36861 21152 "}")
                                             (list "{\\C" str_gcol_p ";"
                                                   36215 28857 20596 12395 36861 21152 "}")))
                                ))
                    ;;直線部を作成するとき、編集中の管路の後ろ側に続くように配置するか手前側に続くように配置するかを選択します
                    (cons "HELP"(lambda()(mix_strasc(list 30452 32218 37096 12434 20316 25104 12377 12427 12392 12365 12289 32232 38598 20013 12398 31649 36335 12398 24460 12429 20596 12395 32154 12367 12424 12358 12395 37197 32622 12377 12427 12363 25163 21069 20596 12395 32154 12367 12424 12358 12395 37197 32622 12377 12427 12363 12434 36984 25246 12375 12414 12377 ))))
                    
                    )
               
               (list(list 53);;編集中の管と保護コンの表示
                    (cons "ITEM"(mix_strasc(list 32232 38598 20013 12398 31649 12392 20445 35703 12467 12531 12398 34920 31034)))
                    (list "PAGE" 1)
                    (cons "INPUTSWITCH"(lambda() (list 'int_hidesolid ls_switch_hidesolid) ))
                    (cons "NOREFERENCE"
                          (setq ls_switch_hidesolid
                                (mapcar 'mix_strasc;;表示非表示
                                        (list(list "{\\C" str_gcol_c ";" 34920 31034 "}")
                                             (list "{\\C" str_gcol_g ";" 38750 34920 31034  "}")
                                             )
                                        )))
                    ;;編集中の管路のモデル部分が非表示になり、深度及び円弧の寸法のみが表示されるように切り替えることができます\n編集を完了すると非表示は終了します
                    (cons "HELP"(lambda()(mix_strasc(list 32232 38598 20013 12398 31649 36335 12398 12514 12487 12523 37096 20998 12364 38750 34920 31034 12395 12394 12426 12289 28145 24230 21450 12403 20870 24359 12398 23544 27861 12398 12415 12364 34920 31034 12373 12428 12427 12424 12358 12395 20999 12426 26367 12360 12427 12371 12392 12364 12391 12365 12414 12377 "\n" 32232 38598 12434 23436 20102 12377 12427 12392 38750 34920 31034 12399 32066 20102 12375 12414 12377 ))))
                    
                    )
               (list(list 54);;経路がないときの深度入力
                    (cons "ITEM"(mix_strasc(list 32076 36335 12364 12394 12356 12392 12365 12398 28145 24230 20837 21147 )))
                    (list "PAGE" 1)
                    (cons "INPUTSWITCH"
                          (lambda()
                            (if int_allow_noroad_temp T(setq int_allow_noroad_temp int_allow_noroad))
                            (list 'int_allow_noroad_temp ls_switch_allow_noroad)
                            ))
                    (cons "NOREFERENCE"
                          (setq ls_switch_allow_noroad
                                (mapcar 'mix_strasc;;表示非表示
                                        (list(list "{\\C" str_gcol_g ";"
                                                   35377 21487 12375 12394 12356 "}")
                                             (list "{\\C" str_gcol_c ";"
                                                   35377 21487 12377 12427 "}")
                                             )
                                        )))
                    ;;経路の選択をしなくてもクリックしたところの地表面標高を取得して深度設定ができる基に切り替えます\n許可しないとき経路を選ばなければ深度設定することはできません
                    (cons "HELP"(lambda()(mix_strasc(list 32076 36335 12398 36984 25246 12434 12375 12394 12367 12390 12418 12463 12522 12483 12463 12375 12383 12392 12371 12429 12398 22320 34920 38754 27161 39640 12434 21462 24471 12375 12390 28145 24230 35373 23450 12364 12391 12365 12427 22522 12395 20999 12426 26367 12360 12414 12377 "\n" 35377 21487 12375 12394 12356 12392 12365 32076 36335 12434 36984 12400 12394 12369 12428 12400 28145 24230 35373 23450 12377 12427 12371 12392 12399 12391 12365 12414 12379 12435 ))))
                    )
               
               (list(list 78);;管の名称
                    (cons "ITEM"(list 31649 12398 21517 31216))
                    (list "PAGE" 0 1)
                    (cons "INPUTSTR"
                          (lambda( / str i bool func)
                            (if(= str_ductname "")(setq str_ductname nil))
                            (if(if str_ductname
                                   (if(or(= int_allow_overwrite 1) vnam_currentinsert)
                                       nil
                                     (null
                                      (vl-catch-all-error-p
                                       (vl-catch-all-apply 'vla-Item(list vnam_blocktable str_ductname))))
                                     )
                                 T)
                                (progn
                                  (setq str "DUCT$" i 0 bool T)
                                  (while bool
                                    (setq i(1+ i)
                                          str_ductname(strcat str(substr(itoa(+ 1000 i))2))
                                          bool
                                          (null
                                           (vl-catch-all-error-p
                                            (vl-catch-all-apply 'vla-Item(list vnam_blocktable str_ductname))))
                                          )
                                    )
                                  ))
                            
                            'str_ductname)
                          )
                    
                    ;; (cons "NO-INPUT"
                    ;;       (lambda()
                    ;;         (if vnam_currentinsert
                    ;;             (progn
                    ;;               (x-alert(list 32232 38598 20013 12399 21517 21069 12398 22793 26356 12399 12391 12365 12414 12379 12435 )) ;;編集中は名前の変更はできません
                    ;;               T))
                    ;;         ))
                    
                    (cons "LOADFUNCTION"
                          (lambda(str / bool)
                            (setq bool
                                  (vl-catch-all-error-p
                                   (vl-catch-all-apply 'vla-Item(list vnam_blocktable str)))
                                  )
                            
                            (if(if bool T
                                 (if(= int_allow_overwrite 0)
                                     (if vnam_currentinsert T)
                                   (progn
                                     (alert
                                      (mix_strasc(list 26082 12395 23384 22312 12377 12427 12502 12525 12483 12463 21517 31216 12391 12377 12364 19978 26360 12365 12373 12428 12414 12377 ))
                                      )
                                     T)))
                                (progn
                                  (if vnam_currentinsert
                                      ((lambda( / vnam )
                                         (setq vnam(vla-Item(vla-get-Blocks(vla-get-ActiveDocument(vlax-get-acad-object)))
                                                            (vla-get-name vnam_currentinsert))
                                               )
                                         (vla-put-name vnam str)
                                         
                                         )))
                                  T
                                  )
                              )
                            )
                          )
                    (cons "STRINPUTALERT"
                          (mix_strasc(list 12502 12525 12483 12463 21517 31216 12364 26082 12395 23384 22312 12375 12390 12356 12414 12377 )))
                    ;;これから作成する管路、編集中の管路の名称を変更します\n管路はブロックとして作成されすでに使用されているブロック名称は設定できません
                    ;;\n名前を付けないとき「DUCT$(使用されていない数値)」を自動的に設定します
                    (cons "HELP"(lambda()(mix_strasc(list 12371 12428 12363 12425 20316 25104 12377 12427 31649 36335 12289 32232 38598 20013 12398 31649 36335 12398 21517 31216 12434 22793 26356 12375 12414 12377 "\n" 31649 36335 12399 12502 12525 12483 12463 12392 12375 12390 20316 25104 12373 12428 12377 12391 12395 20351 29992 12373 12428 12390 12356 12427 12502 12525 12483 12463 21517 31216 12399 35373 23450 12391 12365 12414 12379 12435 "\n" 21517 21069 12434 20184 12369 12394 12356 12392 12365 12300 "DUCT$(" 20351 29992 12373 12428 12390 12356 12394 12356 25968 20516 ")" 12301 12434 33258 21205 30340 12395 35373 23450 12375 12414 12377 ))))
                    )
               
               
               (list(list 77);;モード
                    (cons "ITEM"(mix_strasc(list 12514 12540 12489 20999 26367 )))
                    (list "PAGE" 0 1)
                    (cons "INPUTSWITCH" (lambda() (list 'int_ductmode ls_switch_ductmode )))
                    (cons "NOREFERENCE"
                          (setq ls_switch_ductmode
                                (mapcar 'mix_strasc
                                        (list(list "{\\C" str_gcol_y ";"
                                                   20316 25104 12539 32232 38598 "}")
                                             (list "{\\C" str_gcol_g ";"
                                                   26356 26032 12539 12467 12500 12540 "}")
                                             ;; (list "{\\C" str_gcol_c ";"
                                             ;;       26356 26032 12539 12467 12500 12540 "}")
                                             (list "{\\C" str_gcol_p ";"
                                                   21066 38500 "}")
                                             )))
                          )
                    (cons "LOADFUNCTION"
                          (lambda()
                            
                            (if vnam_road
                                (progn
                                  (if(vl-position vnam_road ls_vnam_killobj)
                                      (progn
                                        (vla-delete vnam_road)
                                        (exckillobj vnam_road)
                                        ))
                                  (setq vnam_road nil
                                        int_ductdepth nil)
                                  ))
                            
                            (mapcar
                             '(lambda(lst)
                                (if(setq lst(assoc "OBJ" lst))
                                    (mapcar
                                     '(lambda(vnam)
                                        (if(=(type vnam)'VLA-OBJECT)
                                            (progn
                                              (vla-delete vnam)
                                              (exckillobj vnam)
                                              ))
                                        )
                                     (cdr lst)))
                                )
                             ls_vnam_duct)
                            (setq ls_vnam_duct nil)


                            (if vnam_currentinsert
                                (progn
                                  (vla-put-visible vnam_currentinsert :vlax-true)
                                  (setq ls_vnam_visible
                                        (vl-remove vnam_currentinsert ls_vnam_visible)
                                        vnam_currentinsert nil)
                                  ))
                            
                            (cond
                             ((= int_ductmode 0)
                              (setq bool_selectent nil bool_select nil int_selectmode -1
                                    ls_ssget nil xtype_ssget nil xdata_ssget nil
                                    vnam_depth nil entna_depth nil
                                    int_ductdepth nil
                                    int_max_duct 0 int_min_duct 0
                                    bool_ductedit nil bool_solidon nil
                                    )
                              
                              )
                             ((= int_ductmode 1)
                              (setq vnam_depth nil entna_depth nil
                                    int_ductdepth nil
                                    bool_ductedit nil
                                    duct_depth 0.)
                              )
                             ((= int_ductmode 2)
                              (setq bool_selectent T bool_select T int_selectmode 0
                                    ls_ssget(list(cons 0 "INSERT"))
                                    xtype_ssget "DUCTBLOCK" xdata_ssget "terraduct3d"
                                    bool_ductedit nil
                                    )
                              )
                             )
                            
                            ))
                    ;;-作成・編集：新規管路の作成または作成済みの管路を選択して編集を行う
                    ;;\n-更新・コピー：深度オフセットが0のとき、モデルを更新,0でないとき適用してコピー
                    ;;\n-削除：管路を選択して削除
                    (cons "HELP"
                          (lambda()
                            (mix_strasc(list "-" 20316 25104 12539 32232 38598 65306 26032 35215 31649 36335 12398 20316 25104 12414 12383 12399 20316 25104 28168 12415 12398 31649 36335 12434 36984 25246 12375 12390 32232 38598 12434 34892 12358
                                             "\n-" 26356 26032 12539 12467 12500 12540 65306 28145 24230 12458 12501 12475 12483 12488 12364 "0" 12398 12392 12365 12289 12514 12487 12523 12434 26356 26032 ",0" 12391 12394 12356 12392 12365 36969 29992 12375 12390 12467 12500 12540
                                             "\n-" 21066 38500 65306 31649 36335 12434 36984 25246 12375 12390 21066 38500
                                             ))))
                    
                    )

               
               (list(list 80 );;P選択モード切替
                    (cons "ITEM"(mix_strasc(list 36984 25246 12514 12540 12489 20999 26367 )))
                    (list "PAGE" 0 1)
                    (cons "INPUTSWITCH"
                          (lambda()
                            (setq int_temp 0)
                            
                            (if(= int_ductmode 2)
                                (if(= int_selectmode -1)
                                    (list nil(mix_strasc
                                              (list "{\\C" str_gcol_p ";"
                                                    21336 20307 36984 25246 12398 12415 "}")))
                                  (list 'int_selectmode
                                        (mapcar 'mix_strasc
                                                (list(list "{\\C" str_gcol_y ";" 36984 25246 "}")
                                                     (list "{\\C" str_gcol_c ";" 35299 38500 "}")))
                                        )
                                  )
                              (list 'int_temp ;;削除モードのとき使用可能
                                    (list(mix_strasc
                                          (list "{\\C" str_gcol_p ";"
                                                21066 38500 12514 12540 12489 12398 12392 12365 20351 29992 21487 33021
                                                "}")))
                                    )
                              )) )
                    (cons "HELP"(lambda()str_guide_selectmode))
                    )
               
               (list(list 65);;A直線部を追加挿入
                    (cons "ITEM"(mix_strasc(list  30452 32218 37096 12434 36861 21152 25407 20837  )))
                    (list "PAGE" 1)
                    (cons "STATUS"
                          (lambda()
                            (mix_strasc
                             (if(apply 'or(mapcar '(lambda(lst)(assoc "LINE" lst))ls_vnam_duct))
                                 (if int_adddepth;;直線部を選択してください,挿入可能
                                     (list "{\\C" str_gcol_y ";" 30452 32218 37096 12434 36984 25246 12375 12390 12367 12384 12373 12356 "}")
                                   (list "{\\C" str_gcol_g ";" 25407 20837 21487 33021 "}")
                                   )
                               (list "{\\C" str_gcol_p ";" ;;直線部がないので挿入できません
                                      30452 32218 37096 12364 12394 12356 12398 12391 25407 20837 12391 12365 12414 12379 12435 "}"))
                             )
                            ))
                    (cons "LOADFUNCTION"
                          (lambda()(if(apply 'or(mapcar '(lambda(lst)(assoc "LINE" lst))ls_vnam_duct))
                                       (progn;;深度を入力して直線部を選択してください
                                         (princ(mix_strasc(list "\n" 28145 24230 12434 20837 21147 12375 12390 30452 32218 37096 12434 36984 25246 12375 12390 12367 12384 12373 12356 )))
                                         (setq int_adddepth 0 )
                                         )
                                     ;;現在の作業において、まだ直線部が生成されていません
                                     (x-alert(list 29694 22312 12398 20316 26989 12395 12362 12356 12390 12289 12414 12384 30452 32218 37096 12364 29983 25104 12373 12428 12390 12356 12414 12379 12435))
                                     ))
                          )
                    
                    (cons "HELP"
                          (lambda()
                            (setq ls_guide_drawing
                                  (list
                                   1
                                   
                                   (list(list -15.0 9.0 0.0)(list 15.0 9.0 0.0)256)
                                   (list(list -11.7321 6.0 0.0)(list -12.0 5.0 0.0)30)
                                   (list(list -12.0 5.0 0.0)(list -12.2679 6.0 0.0)30)
                                   (list(list -12.0 5.0 0.0)(list -12.0 9.0 0.0)30)
                                   (list(list -12.2679 8.0 0.0)(list -12.0 9.0 0.0)30)
                                   (list(list -12.0 9.0 0.0)(list -11.7321 8.0 0.0)30)
                                   (list(list 11.2679 6.0 0.0)(list 11.0 5.0 0.0)30)
                                   (list(list 11.0 5.0 0.0)(list 10.7321 6.0 0.0)30)
                                   (list(list 11.0 5.0 0.0)(list 11.0 9.0 0.0)30)
                                   (list(list 10.7321 8.0 0.0)(list 11.0 9.0 0.0)30)
                                   (list(list 11.0 9.0 0.0)(list 11.2679 8.0 0.0)30)
                                   (list(list -12.0 5.0 0.0)(list 11.0 5.0 0.0)3)
                                   (list(list -15.0 -4.0 0.0)(list 15.0 -4.0 0.0)256)
                                   (list(list -11.7321 -7.0 0.0)(list -12.0 -8.0 0.0)30)
                                   (list(list -12.0 -8.0 0.0)(list -12.2679 -7.0 0.0)30)
                                   (list(list -12.0 -8.0 0.0)(list -12.0 -4.0 0.0)30)
                                   (list(list -12.2679 -5.0 0.0)(list -12.0 -4.0 0.0)30)
                                   (list(list -12.0 -4.0 0.0)(list -11.7321 -5.0 0.0)30)
                                   (list(list 11.2679 -7.0 0.0)(list 11.0 -8.0 0.0)30)
                                   (list(list 11.0 -8.0 0.0)(list 10.7321 -7.0 0.0)30)
                                   (list(list 11.0 -8.0 0.0)(list 11.0 -4.0 0.0)30)
                                   (list(list 10.7321 -5.0 0.0)(list 11.0 -4.0 0.0)30)
                                   (list(list 11.0 -4.0 0.0)(list 11.2679 -5.0 0.0)30)
                                   (list(list -12.0 -8.0 0.0)(list -6.0 -8.0 0.0)3)
                                   (list(list 5.0 -8.0 0.0)(list 11.0 -8.0 0.0)3)
                                   (list(list -4.0 -11.0 0.0)(list 2.0 -11.0 0.0)6)
                                   (list(list -11.7321 -10.0 0.0)(list -12.0 -11.0 0.0)4)
                                   (list(list -12.0 -11.0 0.0)(list -12.2679 -10.0 0.0)4)
                                   (list(list -12.0 -11.0 0.0)(list -12.0 -8.0 0.0)4)
                                   (list(list -12.2679 -9.0 0.0)(list -12.0 -8.0 0.0)4)
                                   (list(list -12.0 -8.0 0.0)(list -11.7321 -9.0 0.0)4)
                                   (list(list -7.87298 -8.0 0.0)(list -7.35182 -8.0691 0.0)6)
                                   (list(list -7.35182 -8.0691 0.0)(list -6.86667 -8.27161 0.0)6)
                                   (list(list -6.86667 -8.27161 0.0)(list -6.45105 -8.59355 0.0)6)
                                   (list(list -6.45105 -8.59355 0.0)(list -6.13368 -9.01266 0.0)6)
                                   (list(list -6.13368 -9.01266 0.0)(list -5.93649 -9.5 0.0)6)
                                   (list(list -4.0 -11.0 0.0)(list -4.52116 -10.9309 0.0)6)
                                   (list(list -4.52116 -10.9309 0.0)(list -5.00631 -10.7284 0.0)6)
                                   (list(list -5.00631 -10.7284 0.0)(list -5.42193 -10.4065 0.0)6)
                                   (list(list -5.42193 -10.4065 0.0)(list -5.7393 -9.98734 0.0)6)
                                   (list(list -5.7393 -9.98734 0.0)(list -5.93649 -9.5 0.0)6)
                                   (list(list 5.87298 -8.0 0.0)(list 5.35182 -8.0691 0.0)6)
                                   (list(list 5.35182 -8.0691 0.0)(list 4.86667 -8.27161 0.0)6)
                                   (list(list 4.86667 -8.27161 0.0)(list 4.45105 -8.59355 0.0)6)
                                   (list(list 4.45105 -8.59355 0.0)(list 4.13368 -9.01266 0.0)6)
                                   (list(list 4.13368 -9.01266 0.0)(list 3.93649 -9.5 0.0)6)
                                   (list(list 2.0 -11.0 0.0)(list 2.52116 -10.9309 0.0)6)
                                   (list(list 2.52116 -10.9309 0.0)(list 3.00631 -10.7284 0.0)6)
                                   (list(list 3.00631 -10.7284 0.0)(list 3.42193 -10.4065 0.0)6)
                                   (list(list 3.42193 -10.4065 0.0)(list 3.7393 -9.98734 0.0)6)
                                   (list(list 3.7393 -9.98734 0.0)(list 3.93649 -9.5 0.0)6)
                                   (list(list -3.73205 -10.0 0.0)(list -4.0 -11.0 0.0)30)
                                   (list(list -4.0 -11.0 0.0)(list -4.26795 -10.0 0.0)30)
                                   (list(list -4.0 -11.0 0.0)(list -4.0 -4.0 0.0)30)
                                   (list(list -4.26795 -5.0 0.0)(list -4.0 -4.0 0.0)30)
                                   (list(list -4.0 -4.0 0.0)(list -3.73205 -5.0 0.0)30)
                                   (list(list 2.26795 -10.0 0.0)(list 2.0 -11.0 0.0)30)
                                   (list(list 2.0 -11.0 0.0)(list 1.73205 -10.0 0.0)30)
                                   (list(list 2.0 -11.0 0.0)(list 2.0 -4.0 0.0)30)
                                   (list(list 1.73205 -5.0 0.0)(list 2.0 -4.0 0.0)30)
                                   (list(list 2.0 -4.0 0.0)(list 2.26795 -5.0 0.0)30)
                                   (list(list 8.66123 4.33552 0.0)(list 9.1595 3.66803 0.0)3)
                                   (list(list 8.16061 3.66803 0.0)(list 8.66123 4.33552 0.0)3)
                                   (list(list 8.66123 4.33552 0.0)(list 8.66123 2.16852 0.0)3)
                                   (list(list 12.4429 2.32364 0.0)(list 12.6591 2.16852 0.0)3)
                                   (list(list 12.1233 2.55632 0.0)(list 12.4429 2.32364 0.0)3)
                                   (list(list 11.4793 2.32364 0.0)(list 11.6932 2.47876 0.0)3)
                                   (list(list 11.1596 2.16852 0.0)(list 11.4793 2.32364 0.0)3)
                                   (list(list 12.1233 3.33428 0.0)(list 12.1233 2.63388 0.0)3)
                                   (list(list 11.6932 3.33428 0.0)(list 11.6932 2.63388 0.0)3)
                                   (list(list 11.1596 2.63388 0.0)(list 12.6591 2.63388 0.0)3)
                                   (list(list 11.3735 3.02404 0.0)(list 12.4429 3.02404 0.0)3)
                                   (list(list 12.6591 3.55756 0.0)(list 12.6591 3.72444 0.0)3)
                                   (list(list 12.6098 3.50116 0.0)(list 12.6591 3.55756 0.0)3)
                                   (list(list 12.0387 3.50116 0.0)(list 12.6098 3.50116 0.0)3)
                                   (list(list 11.9917 3.55756 0.0)(list 12.0387 3.50116 0.0)3)
                                   (list(list 11.9917 3.94537 0.0)(list 11.9917 3.55756 0.0)3)
                                   (list(list 12.5628 3.94537 0.0)(list 11.9917 3.94537 0.0)3)
                                   (list(list 12.5628 4.33552 0.0)(list 12.5628 3.94537 0.0)3)
                                   (list(list 12.0387 4.33552 0.0)(list 12.5628 4.33552 0.0)3)
                                   (list(list 11.8248 3.55756 0.0)(list 11.8248 3.72444 0.0)3)
                                   (list(list 11.7778 3.50116 0.0)(list 11.8248 3.55756 0.0)3)
                                   (list(list 11.2066 3.50116 0.0)(list 11.7778 3.50116 0.0)3)
                                   (list(list 11.1596 3.55756 0.0)(list 11.2066 3.50116 0.0)3)
                                   (list(list 11.1596 3.94537 0.0)(list 11.1596 3.55756 0.0)3)
                                   (list(list 11.7308 3.94537 0.0)(list 11.1596 3.94537 0.0)3)
                                   (list(list 11.7308 4.33552 0.0)(list 11.7308 3.94537 0.0)3)
                                   (list(list 11.2066 4.33552 0.0)(list 11.7308 4.33552 0.0)3)
                                   (list(list 11.491 2.00164 0.0)(list 12.8237 2.00164 0.0)3)
                                   (list(list 10.9928 2.15677 0.0)(list 11.491 2.00164 0.0)3)
                                   (list(list 10.8259 2.31189 0.0)(list 10.9928 2.15677 0.0)3)
                                   (list(list 10.8259 2.31189 0.0)(list 10.4921 2.00164 0.0)3)
                                   (list(list 10.8259 3.40009 0.0)(list 10.8259 2.31189 0.0)3)
                                   (list(list 10.4921 3.40009 0.0)(list 10.8259 3.40009 0.0)3)
                                   (list(list 10.659 4.33552 0.0)(list 10.8259 3.86781 0.0)3)
                                   (list(list 14.5136 4.33552 0.0)(list 15.5853 4.33552 0.0)3)
                                   (list(list 15.4654 2.15677 0.0)(list 15.8227 2.00164 0.0)3)
                                   (list(list 14.9907 2.7796 0.0)(list 15.4654 2.15677 0.0)3)
                                   (list(list 14.8708 3.08985 0.0)(list 14.9907 2.7796 0.0)3)
                                   (list(list 14.8708 3.40009 0.0)(list 14.8708 3.08985 0.0)3)
                                   (list(list 14.396 2.62448 0.0)(list 14.1563 2.00164 0.0)3)
                                   (list(list 14.5136 3.24497 0.0)(list 14.396 2.62448 0.0)3)
                                   (list(list 14.5136 4.33552 0.0)(list 14.5136 3.24497 0.0)3)
                                   (list(list 15.5853 3.40009 0.0)(list 14.5136 3.40009 0.0)3)
                                   (list(list 15.5853 4.33552 0.0)(list 15.5853 3.40009 0.0)3)
                                   (list(list 14.5136 4.33552 0.0)(list 15.5853 4.33552 0.0)3)
                                   (list(list 14.1446 3.00054 0.0)(list 14.2644 3.16741 0.0)3)
                                   (list(list 13.9072 2.83366 0.0)(list 14.1446 3.00054 0.0)3)
                                   (list(list 13.5499 2.66679 0.0)(list 13.9072 2.83366 0.0)3)
                                   (list(list 13.9072 2.00164 0.0)(list 13.7873 2.00164 0.0)3)
                                   (list(list 13.9072 4.50005 0.0)(list 13.9072 2.00164 0.0)3)
                                   (list(list 13.5499 3.8349 0.0)(list 14.2644 3.8349 0.0)3)
                                   (list(list -0.335853 -1.33113 0.0)(list -0.335853 1.6679 0.0)2)
                                   (list(list 0.331642 1.6679 0.0)(list 0.331642 -1.33113 0.0)2)
                                   (list(list 0.996787 -0.665986 0.0)(list -0.00210513 -1.66488 0.0)2)
                                   (list(list -0.00210513 -1.66488 0.0)(list -1.001 -0.665986 0.0)2)
                                   (list(list -19.7966 -8.99897 0.0)(list -19.5302 -8.99897 0.0)4)
                                   (list(list -19.5302 -8.99897 0.0)(list -19.5302 -9.39851 0.0)4)
                                   (list(list -19.5302 -9.39851 0.0)(list -19.6634 -9.66487 0.0)4)
                                   (list(list -19.6634 -9.66487 0.0)(list -19.9964 -9.99782 0.0)4)
                                   (list(list -19.5302 -9.39851 0.0)(list -19.3971 -9.66487 0.0)4)
                                   (list(list -19.3971 -9.66487 0.0)(list -19.0617 -9.99782 0.0)4)
                                   (list(list -18.0628 -9.99782 0.0)(list -17.9296 -9.86464 0.0)4)
                                   (list(list -17.9296 -9.86464 0.0)(list -17.9296 -9.26533 0.0)4)
                                   (list(list -17.9296 -9.26533 0.0)(list -18.7953 -9.26533 0.0)4)
                                   (list(list -18.6621 -9.86464 0.0)(list -18.7953 -9.99782 0.0)4)
                                   (list(list -18.4623 -9.59828 0.0)(list -18.6621 -9.86464 0.0)4)
                                   (list(list -18.3957 -9.26533 0.0)(list -18.4623 -9.59828 0.0)4)
                                   (list(list -18.3957 -8.99897 0.0)(list -18.3957 -9.26533 0.0)4)
                                   (list(list -18.196 -9.99782 0.0)(list -18.0628 -9.99782 0.0)4)
                                   (list(list -17.2637 -9.06556 0.0)(list -16.6644 -9.06556 0.0)4)
                                   (list(list -16.6644 -9.06556 0.0)(list -16.6644 -9.19874 0.0)4)
                                   (list(list -16.9308 -9.39851 0.0)(list -16.6644 -9.39851 0.0)4)
                                   (list(list -16.6644 -9.39851 0.0)(list -16.6644 -9.33192 0.0)4)
                                   (list(list -17.2637 -9.59828 0.0)(list -16.6644 -9.59828 0.0)4)
                                   (list(list -17.2637 -9.06556 0.0)(list -17.2637 -9.19874 0.0)4)
                                   (list(list -16.9974 -9.4651 0.0)(list -16.9974 -9.99782 0.0)4)
                                   (list(list -16.9308 -9.06556 0.0)(list -16.9308 -9.39851 0.0)4)
                                   (list(list -17.5301 -8.99897 0.0)(list -17.3969 -9.13215 0.0)4)
                                   (list(list -17.5967 -9.26533 0.0)(list -17.4635 -9.39851 0.0)4)
                                   (list(list -17.5967 -9.99782 0.0)(list -17.3969 -9.59828 0.0)4)
                                   (list(list -17.0639 -9.06556 0.0)(list -17.0639 -9.13215 0.0)4)
                                   (list(list -17.0639 -9.13215 0.0)(list -17.1305 -9.26533 0.0)4)
                                   (list(list -17.1305 -9.26533 0.0)(list -17.2637 -9.39851 0.0)4)
                                   (list(list -16.9974 -9.59828 0.0)(list -17.2637 -9.93123 0.0)4)
                                   (list(list -17.2637 -9.93123 0.0)(list -17.3303 -9.93123 0.0)4)
                                   (list(list -16.9974 -9.59828 0.0)(list -16.731 -9.93123 0.0)4)
                                   (list(list -16.731 -9.93123 0.0)(list -16.6644 -9.93123 0.0)4)
                                   (list(list -15.8653 -9.86464 0.0)(list -15.4658 -9.99782 0.0)4)
                                   (list(list -16.0651 -9.73146 0.0)(list -15.8653 -9.86464 0.0)4)
                                   (list(list -15.7987 -9.86464 0.0)(list -16.1983 -9.99782 0.0)4)
                                   (list(list -15.599 -9.73146 0.0)(list -15.7987 -9.86464 0.0)4)
                                   (list(list -15.599 -9.66487 0.0)(list -15.599 -9.73146 0.0)4)
                                   (list(list -16.1317 -9.66487 0.0)(list -15.599 -9.66487 0.0)4)
                                   (list(list -16.2649 -9.79805 0.0)(list -16.398 -9.99782 0.0)4)
                                   (list(list -16.2649 -9.13215 0.0)(list -16.2649 -9.79805 0.0)4)
                                   (list(list -15.6656 -9.13215 0.0)(list -15.6656 -9.53169 0.0)4)
                                   (list(list -15.6656 -9.53169 0.0)(list -15.9985 -9.53169 0.0)4)
                                   (list(list -15.9985 -9.53169 0.0)(list -15.9985 -9.13215 0.0)4)
                                   (list(list -15.8653 -8.99897 0.0)(list -15.8653 -9.13215 0.0)4)
                                   (list(list -16.1317 -9.33192 0.0)(list -15.5324 -9.33192 0.0)4)
                                   (list(list -16.2649 -9.13215 0.0)(list -15.4658 -9.13215 0.0)4)
                                   (list(list -14.4373 -9.14201 0.0)(list -15.197 -9.56868 0.0)4)
                                   (list(list -15.197 -9.56868 0.0)(list -14.4373 -9.99782 0.0)4)
                                   (list(list -14.1981 -9.23573 0.0)(list -14.1981 -9.18887 0.0)4)
                                   (list(list -14.1981 -9.18887 0.0)(list -14.1512 -9.09269 0.0)4)
                                   (list(list -14.1512 -9.09269 0.0)(list -14.1044 -9.04583 0.0)4)
                                   (list(list -14.1044 -9.04583 0.0)(list -14.0082 -8.99897 0.0)4)
                                   (list(list -14.0082 -8.99897 0.0)(list -13.8183 -8.99897 0.0)4)
                                   (list(list -13.8183 -8.99897 0.0)(list -13.7221 -9.04583 0.0)4)
                                   (list(list -13.7221 -9.04583 0.0)(list -13.6752 -9.09269 0.0)4)
                                   (list(list -13.6752 -9.09269 0.0)(list -13.6284 -9.18887 0.0)4)
                                   (list(list -13.6284 -9.18887 0.0)(list -13.6284 -9.28506 0.0)4)
                                   (list(list -13.6284 -9.28506 0.0)(list -13.6752 -9.37878 0.0)4)
                                   (list(list -13.6752 -9.37878 0.0)(list -13.7714 -9.52182 0.0)4)
                                   (list(list -13.7714 -9.52182 0.0)(list -14.2474 -9.99782 0.0)4)
                                   (list(list -14.2474 -9.99782 0.0)(list -13.5791 -9.99782 0.0)4)
                                   (list(list -13.2954 -9.99782 0.0)(list -13.2954 -8.99897 0.0)4)
                                   (list(list -13.2954 -8.99897 0.0)(list -12.8663 -8.99897 0.0)4)
                                   (list(list -12.8663 -8.99897 0.0)(list -12.7233 -9.04583 0.0)4)
                                   (list(list -12.7233 -9.04583 0.0)(list -12.6764 -9.09269 0.0)4)
                                   (list(list -12.6764 -9.09269 0.0)(list -12.6271 -9.18887 0.0)4)
                                   (list(list -12.6271 -9.18887 0.0)(list -12.6271 -9.28506 0.0)4)
                                   (list(list -12.6271 -9.28506 0.0)(list -12.6764 -9.37878 0.0)4)
                                   (list(list -12.6764 -9.37878 0.0)(list -12.7233 -9.4281 0.0)4)
                                   (list(list -12.7233 -9.4281 0.0)(list -12.8663 -9.47496 0.0)4)
                                   (list(list -12.8663 -9.47496 0.0)(list -13.2954 -9.47496 0.0)4)
                                   (list(list -12.9625 -9.47496 0.0)(list -12.6271 -9.99782 0.0)4)

                                   ))

                            ;;直線部を選択して直線部を追加します\n一旦、下方向に曲げ半径の1/5倍の値でオフセットさせるので深度を調整してください
                            (mix_strasc(list 30452 32218 37096 12434 36984 25246 12375 12390 30452 32218 37096 12434 36861 21152 12375 12414 12377 "\n" 19968 26086 12289 19979 26041 21521 12395 26354 12370 21322 24452 12398 "1/5" 20493 12398 20516 12391 12458 12501 12475 12483 12488 12373 12379 12427 12398 12391 28145 24230 12434 35519 25972 12375 12390 12367 12384 12373 12356 str_startguidedrawing ))))

                    
                    )

               (list(list 88);;X基準となる線形を変更
                    (cons "ITEM"(mix_strasc(list 22522 28310 12392 12394 12427 32218 24418 12434 22793 26356  )))
                    (list "PAGE" 1)
                    (cons "STATUS"
                          (lambda()
                            (mix_strasc
                             (if ls_vnam_duct
                                 (if ls_exchangelevel;;個選択中/線形選択で完了
                                     (list "{\\C" str_gcol_y "; "(as-numstr(1-(length ls_exchangelevel))) " }"
                                           20491 36984 25246 20013 " / "
                                           "{\\C" str_gcol_g ";" 32218 24418 36984 25246 12391 23436 20102 "}")
                                   (list "{\\C" str_gcol_g ";" 23455 34892 21487 33021 "}")
                                   )
                               (list "{\\C" str_gcol_p ";" ;;管路編集中に実行可能
                                     31649 36335 32232 38598 20013 12395 23455 34892 21487 33021 "}"))
                             )
                            ))
                    (cons "LOADFUNCTION"
                          (lambda()(if ls_vnam_duct
                                       (progn;;変更する深さ寸法を選択し、変更先の線形を選択してください
                                         (princ(mix_strasc(list 28145 24230 12434 20837 21147 12375 12390 30452 32218 37096 12434 36984 25246 12375 12390 12367 12384 12373 12356 )))
                                         (setq ls_exchangelevel (list nil))
                                         )
                                     ;;管路編集中に使用できる機能です
                                     (x-alert(list 31649 36335 32232 38598 20013 12395 20351 29992 12391 12365 12427 27231 33021 12391 12377 ))
                                     ))
                          )
                    
                    (cons "HELP"
                          (lambda()
                            ;;基準となる線形を変更したいときに使用\n変更する深さ寸法をクリックで選択後、線形を選択すると基準を変更することができます\n基本的にZ方向の変分のみを想定した機能ですが、平面的に形状が異なる線形も対象にできます\n平面的に形状が異なる線形を対象にしたとき、高さ変化が大きすぎるとき\n円弧形状が破綻する可能性があるので必要に応じて修正してください
                            (mix_strasc
                             (list 22522 28310 12392 12394 12427 32218 24418 12434 22793 26356 12375 12383 12356 12392 12365 12395 20351 29992
                                   "\n" 22793 26356 12377 12427 28145 12373 23544 27861 12434 12463 12522 12483 12463 12391 36984 25246 24460 12289 32218 24418 12434 36984 25246 12377 12427 12392 22522 28310 12434 22793 26356 12377 12427 12371 12392 12364 12391 12365 12414 12377
                                   "\n" 22522 26412 30340 12395 "Z" 26041 21521 12398 22793 20998 12398 12415 12434 24819 23450 12375 12383 27231 33021 12391 12377 12364 12289 24179 38754 30340 12395 24418 29366 12364 30064 12394 12427 32218 24418 12418 23550 35937 12395 12391 12365 12414 12377
                                   "\n" 24179 38754 30340 12395 24418 29366 12364 30064 12394 12427 32218 24418 12434 23550 35937 12395 12375 12383 12392 12365 12289 39640 12373 22793 21270 12364 22823 12365 12377 12366 12427 12392 12365 
                                   "\n" 20870 24359 24418 29366 12364 30772 32187 12377 12427 21487 33021 24615 12364 12354 12427 12398 12391 24517 35201 12395 24540 12376 12390 20462 27491 12375 12390 12367 12384 12373 12356  ))))
                    
                    
                    )
               
               (list(list 69);;E直線部の起終点と深さ寸法の位置を合わせる
                    (cons "ITEM"(mix_strasc(list 30452 32218 37096 12398 36215 32066 28857 12392 28145 12373 23544 27861 12398 20301 32622 12434 21512 12431 12379 12427 )))
                    (list "PAGE" 1)
                    (cons "STATUS"
                          (lambda()
                            (mix_strasc
                             (if(and ls_vnam_duct
                                     (or str_lasground height_ground))
                                 (list "{\\C" str_gcol_g ";" 23455 34892 21487 33021 "}")
                               (list "{\\C" str_gcol_p ";" ;;標高設定があり管路編集中に実行可能
                                     31649 36335 32232 38598 20013 12395 23455 34892 21487 33021 "}"))
                             )
                            ))
                    (cons "LOADFUNCTION"
                          (lambda()(if(and ls_vnam_duct
                                           (or str_lasground height_ground ))
                                       ((lambda( / ii jj lst p0 p1 entna pg str bool)
                                          (setq ii 0 jj 0 bool T)
                                          (while(setq lst(assoc(list "ARC" ii jj)ls_vnam_duct))
                                            (setq entna(cadr(assoc "OBJ" lst)))
                                            (if(= jj 0)
                                                (setq jj 1 p0(cdr(assoc 13(entget entna))))
                                              (setq ii(1+ ii)jj 0 p0(cdr(assoc 14(entget entna))))
                                              )
                                            
                                            (setq lst(assoc(list "DEPTH" ii jj)ls_vnam_duct)
                                                  entna(cadr(assoc "OBJ" lst))
                                                  lst(entget entna) )
                                            (if(setq pg(car(project_to_ground
                                                            (list p0)(list 0 0 1)
                                                            (list str_lasground height_ground))))
                                                (make_2pdimension
                                                 entna(list pg p0(cdr(assoc 210 lst))nil
                                                            nil(* 0.5 pi) 0.
                                                            (depth_level_str pg p0)
                                                            str_dimstyle_ductlevel))
                                              )
                                            )
                                          
                                          
                                          ))
                                     ;;標高設定があり管路編集中に使用できる機能です
                                     (x-alert(list 27161 39640 35373 23450 12364 12354 12426 12289
                                                   31649 36335 32232 38598 20013 12395 20351 29992 12391 12365 12427 27231 33021 12391 12377 ))
                                     ))
                          )
                    
                    (cons "HELP"
                          (lambda()
                            ;;深さ寸法が直線部の両端になるように調整します\n経路を使用している場合、経路からはみ出す可能性もあります
                            (mix_strasc
                             (list 28145 12373 23544 27861 12364 30452 32218 37096 12398 20001 31471 12395 12394 12427 12424 12358 12395 35519 25972 12375 12414 12377 "\n" 32076 36335 12434 20351 29992 12375 12390 12356 12427 22580 21512 12289 32076 36335 12363 12425 12399 12415 20986 12377 21487 33021 24615 12418 12354 12426 12414 12377  ))))
                    
                    )
               
               
               (list(list nil)
                    (cons "ITEM"(list ))
                    (cons "BOOL"
                          (lambda()
                            T
                            ))
                    (cons
                     "STATUS"
                     (lambda( / bool_depth ii ls_out)

                       (setq ls_out
                             (cond
                              ((= int_ductmode 0);;作成編集
                               (if(or ls_vnam_duct bool_ductedit)
                                   (list
                                    (list
                                     "{\\C" str_gcol_y ";" 31649 36335 32232 38598 20013 " " 9733 "}"
                                     (if(=(type elem_grread)'LIST)
                                         ((lambda(ls_dummy / str lst vnam p vec) 
                                            (while ls_dummy
                                              (setq lst(car ls_dummy)ls_dummy(cdr ls_dummy)
                                                    vnam(car lst)p(cdr lst))
                                              (if(vlax-erased-p vnam)
                                                  (setq ls_p_dimtext(vl-remove lst ls_p_dimtext))
                                                (progn
                                                  (setq vec(mapcar '- p elem_grread))
                                                  (if(<(+(abs(apply '+(mapcar '* vec vec_x_onview)))
                                                         (abs(apply '+(mapcar '* vec vec_y_onview))))
                                                       (* 2 height_text))
                                                      (setq str(vla-get-TextOverride vnam)
                                                            str(vl-string-subst
                                                                (rtos(vla-get-Measurement vnam)2 3)
                                                                "<>" str)
                                                            str(vl-string-subst " , " "\\P" str)
                                                            
                                                            ls_dummy nil)
                                                    )
                                                  ))
                                              )
                                            (if str(list 12304 str 12305))
                                            )
                                          ls_p_dimtext))
                                     )
                                    (list
                                     "{\\C" str_gcol_g ";" 30452 32218 37096 "{\\C"
                                     ((lambda( / ii)
                                        (setq ii 0)
                                        (mapcar '(lambda(lst)
                                                   (if(assoc "DEPTH" lst)(setq ii(1+ ii))))
                                                ls_vnam_duct)
                                        (if(=(rem ii 2)0)
                                            (list str_gcol_y "; " "< 1 > ");;9312);;9313))
                                          (list str_gcol_c "; " "< 2 > "))
                                        ))
                                     "}" 28857 30446 12434 36984 25246 "} " 12304 "{\\C"
                                     (if vnam_road
                                         (list str_gcol_c ";" 32076 36335 36984 25246 12354 12426)
                                       (list str_gcol_p ";" 32076 36335 36984 25246 12394 12375 )
                                       );;経路選択ありなし
                                     "}" 12305
                                     )
                                    (list
                                     "   {\\C" str_gcol_p ";"
                                     28145 24230 "(" 25991 23383 ")};" 28145 12373 22793 26356
                                     " , {\\C" str_gcol_p ";"
                                     28145 24230 "(" 25991 23383 20197 22806 ")};" 20301 32622 22793 26356
                                     ;;深さ寸法(文字);深さ変更,深さ寸法(文字以外);位置変更
                                     )
                                    (list
                                     "   {\\C" str_gcol_p ";"
                                     20870 24359 "(" 25991 23383 ")};" 26354 12370 21322 24452
                                     " , {\\C" str_gcol_p ";"
                                     20870 24359 "(" 25991 23383 20197 22806 ")};"
                                     20301 32622 22793 26356 "(" 21487 33021 12394 26178 12398 12415 ")" 
                                     ;;円弧部;曲げ半径,
                                     )
                                    (list
                                     "   {\\C" str_gcol_p ";" 30452 32218 37096 "};"
                                     30452 32218 37096 12434 21066 38500
                                     (if int_selectmenu T
                                       (list " , {\\C" str_gcol_p ";Enter}; : " 24418 29366 30906 23450))
                                     ;;直線部;直線部を削除,その他;直線部の追加
                                     )
                                    ;; (if(if entna_depth
                                    ;;        ((lambda(lst / ii)
                                    ;;           (setq ii -1)
                                    ;;           (while lst
                                    ;;             (if(assoc "LINE"(car lst))(setq ii(1+ ii)))
                                    ;;             (if(= ii 2)(setq lst nil)
                                    ;;               (setq lst(cdr lst)))
                                    ;;             )
                                    ;;           (= ii 2))
                                    ;;         ls_vnam_duct))
                                    ;;     (list "   {\\C" str_gcol_c ";F : "
                                    ;;           20182 12398 "3" 28857 12434 36984 25246 12375 12390 21516 19968 24179 38754 12395 12394 12427 12424 12358 12395 28145 24230 12434 35519 25972 12377 12427 ))
                                    ;; ;;他の3点を選択して同一平面になるように深度を調整する
                                    
                                    )
                                 
                                 (list
                                  (list
                                   "{\\C" str_gcol_g ";"
                                   " - " 32218 24418 12458 12502 12472 12455 12463 12488 12434 36984 25246 12375 12390
                                   32076 36335 12354 12426 12391 26032 35215 20316 25104 38283 22987
                                   ;;線形オブジェクトを選択して経路ありで新規作成開始
                                   )
                                  (list
                                   " - " 20219 24847 28857 12434 12463 12522 12483 12463 12375 12390
                                   32076 36335 12394 12375 12391 26032 35215 20316 25104 38283 22987
                                   ;;任意点をクリックして経路なしで新規作成開始
                                   )
                                  (list
                                   " - " 20316 25104 28168 12415 12398 31649 36335 12434 36984 25246
                                   32232 38598 38283 22987
                                   ;;作成済みの管路を選択して編集開始
                                   )

                                  (list " - " 12300 "R=" 8734 12301 12399 20870 24359 12364 12394 12356 12371 12392 12434 34920 12377 )
                                  ;;「R=∞」は円弧がないことを表す
                                  (list " - " 32232 38598 38283 22987 26178 12289 27425 12398 25805 20316 12434 12377 12427 12414 12391 12399 12477 12522 12483 12489 12364 38750 34920 31034 12395 12394 12426 12414 12377  "}")
                                  ;;編集開始時、次の操作をするまではソリッドが非表示になります
                                  
                                  
                                  )
                                 )
                               )
                              
                              ((= int_ductmode 1);;更新コピー
                               (list
                                (list
                                 " - " "{\\C" str_gcol_y ";"
                                 20316 25104 28168 12415 12398 31649 36335 12434 12463 12522 12483 12463 12377 12427 12392 23455 34892 "}"
                                 ;;作成済みの管路をクリックすると実行
                                 )
                                (list
                                 " - " "{\\C" str_gcol_g ";"
                                  12300 28145 24230 12301 12300 12458 12501 12475 12483 12488 12301 12364 12356 12378 12428 12418 "0" 12398 12392 12365 12289 29694 22312 35373 23450 12373 12428 12390 12356 12427 12497 12521 12513 12540 12479 12391 26356 26032 "}"
                                  )
                                (list
                                 " - " "{\\C" str_gcol_g ";"
                                 12381 12398 20182 12398 20516 12434 20837 21147 12375 12383 12392 12365 12289 36984 25246 12373 12428 12383 31649 36335 12398 12497 12521 12513 12540 12479 12434 20351 12387 12390 12467 12500 12540 "}"
                                 )
                                (list
                                 " - " "{\\C" str_gcol_c ";"
                                 "( " 12300 28145 24230 12301 12399 29694 22312 12398 20301 32622 12363 12425 12398 28145 24230 12434 20837 21147 " )}"
                                 )
                                ;;「深度」「オフセット」がいずれも0のとき、現在設定されているパラメータで更新
                                ;;その他の値を入力したとき、選択された管路のパラメータを使ってコピー
                                ;;「深度」は現在の位置からの深度を入力
                                
                                )
                               )
                              ((= int_ductmode 2) ;;削除
                               (list
                                (list
                                 "{\\C" str_gcol_p ";"
                                 " - " 31649 36335 12434 36984 25246 12375 12390 "Enter : "
                                 21066 38500 "}"
                                 ;;管路を選択してEnter:削除
                                 )
                                )
                               )
                              );;cond
                             ls_out(vl-remove nil ls_out)
                             )
                       ls_out
                       ))
                    )
               
               (list(list "ENTER");;メインメニューへ
                    (cons "ITEM"(mix_strasc(list 12513 12452 12531 12513 12491 12517 12540 12408)))
                    (cons "LOADFUNCTION"
                          (lambda()
                            (setq str_next
                                  (if bool_ductedit
                                      (if ls_vnam_duct nil "home")
                                    "home"))

                            ;; (if(if bool_ductedit ls_vnam_duct)
                            ;;     (setq str_next nil )
                            ;;   (progn
                            ;;     (setq str_next "home")
                            ;;     (mapcar
                            ;;      '(lambda(lst)
                            ;;         (mapcar '(lambda(v)
                                               
                            ;;                    (if(=(type v)'VLA-OBJECT)
                            ;;                        (progn
                            ;;                          (vl-delete a)
                            ;;                          (exckillobj v)))
                            ;;                    )
                            ;;                 (cdr(assoc "OBJ" lst)))
                            ;;         )
                            ;;      ls_vnam_duct)
                            ;;     (setq ls_vnam_duct nil)
                            ;;     ))
                            
                            ))
                    (cons "NEXTMODE" "home")
                    )
               )
              )
             
             (setq func_selectmenu_ductedit_depth
                   (lambda(lst / a ii)
                     (setq ii -1)
                     (while lst
                       (setq a(car lst)lst(cdr lst)ii(1+ ii))
                       (if(vl-position(cons "KEYSEARCH" "DEPTH")a)(setq lst nil))
                       )
                     ii)
                   
                   
                   func_selectmenu_ductedit_offset
                   (lambda(lst / a ii)
                     (setq ii -1)
                     (while lst
                       (setq a(car lst)lst(cdr lst)ii(1+ ii))
                       (if(vl-position(cons "KEYSEARCH" "OFFSET")a)(setq lst nil))
                       )
                     ii)
                   )
             
             
             ))
       
       (if(cadr bool) (list ) )
       ))


    (cons
     "MOVE"
     (lambda( / p);;(d- gr5_home()(progn))
       
       (if(setq vnam(cadr(assoc "OBJ"(assoc(list "SOLID" 0)ls_vnam_duct))))
           ((lambda(bool / visble-1 visible-2)
              (if(if bool(null bool_firsttime_editduct))
                  (setq visible-1 :vlax-false visible-2 :vlax-true)
                (setq visible-1 :vlax-true visible-2 :vlax-false))
              
              (if(=(vla-get-visible vnam)visible-1)
                  (progn(vla-put-visible vnam visible-2)
                        (if(setq vnam(cadr(assoc "OBJ"(assoc(list "MESH" 0)ls_vnam_duct))))
                            (vla-put-visible vnam visible-2)))))
            (= int_hidesolid 0)))

       
       ;;p_roadclick_temp
       (cond
        ((or(= int_editdepth 2)(null int_selectmenu_ductedit))
         
         (setq p_ground elem_grread)
         (setq p_click p_ground)


         
         (if(vl-position int_ductdepth(list 0 1))
             
             (if(if(or str_lasground height_ground)
                    ((lambda( / bool)
                       (if(setq p(car(project_to_ground
                                      (list p_ground)vec_view
                                      (list str_lasground height_ground))))
                           (setq p_ground p bool T)
                         (progn;;
                           
                           (setq ls_p
                                 (project_to_ground
                                  (mapcar '(lambda(a)(mapcar '+ p_ground a))
                                          (list(list size_grid 0. 0.) (list (- size_grid)0. 0.)
                                               (list 0. size_grid 0.) (list 0.(- size_grid)0.)))
                                  vec_view(list str_lasground height_ground))
                                 )
                           (if(setq ls_p(vl-remove nil ls_p))
                               (setq nn(length ls_p)
                                     p_ground(mapcar '(lambda(func)(/(apply '+(mapcar 'func ls_p))nn))
                                                     (list car cadr caddr))
                                     bool T
                                     )
                             )
                           )
                         )
                       bool)))
                 T
               (if ls_p_road
                   (setq p_ground
                         ((lambda(p v / z cosdist d n bool zc )

                            (setq z(/(apply
                                      '+(mapcar
                                         '(lambda(p)(apply '+(mapcar '* v p)))
                                         ls_p_road))
                                     (length ls_p_road))
                                  zc(apply '+(mapcar '* v p))
                                  zc(- z zc)
                                  )
                            (mapcar '(lambda(a b)(+ a(* zc b)))p v)
                            
                            ;; (setq cosdist(caddr v))
                            ;; (if(<(abs cosdist)1e-8) (setq p(carxyz p z))
                            ;;   (setq d(/(- z(caddr p))cosdist)
                            ;;         p(mapcar '(lambda(a b)(+ a(* d b)))p v)) )
                            )
                          p_ground vec_view
                          ;;(/(apply '+(mapcar 'caddr ls_p_road))(length ls_p_road))
                          )
                         )
                 )
               ))

         
         (if vnam_road
             (if(setq p_close(vlax-curve-getclosestpointto vnam_road p_ground nil))
                 ((lambda(ls_p / p vec vec1 vec2 x y ang ang1 ang2 d pn dn)
                    (while ls_p
                      (setq p(car ls_p)ls_p(cdr ls_p)
                            d(distance p p_close))
                      (if(< d 0.2)
                          (setq pn(if(car ls_p)(car ls_p))
                                dn(if pn(distance pn p_close))
                                p_close(if(if dn(< dn d))pn p)
                                ls_p nil
                                )
                        )
                      )
                    
                    (if(setq vec_road(xvla-normal vnam_road p_close))
                        (progn
                          (setq vec(trans-x vec_road(list 0 0 1)vec_view)
                                ang(atan(cadr vec)(car vec))
                                ang(+ ang(* 0.9 pi))
                                vec1(list(cos ang)(sin ang)0.)
                                vec1(trans-x vec1 vec_view(list 0 0 1))
                                ang(+ ang(* 0.2 pi))
                                vec2(list(cos ang)(sin ang)0.)
                                vec2(trans-x vec2 vec_view(list 0 0 1))
                                
                                )
                          
                          (mapcar
                           '(lambda(v)
                              (grdraw p_close(mapcar '(lambda(a b)(+ a(* height_text 3. b)))p_close v) 3))
                           (list vec1 vec2))
                          ))
                    (grdraw p_ground p_close 2)
                    (setq p_ground p_close)

                    (if(= int_inputdepth_temp 2)T
                      ((lambda(p c / s ls_p p0 p1 p2)
                         (setq s(* height_text 8.(if(= int_inputdepth_temp 0)1 -1))
                               p0(mapcar '+ p(list 0 0 s))
                               p1(mapcar '(lambda(a x y)(+ a(*  0.1 s x)(* -0.3 s y)))
                                         p0 vec_x_onview vec_y_onview)
                               p2(mapcar '(lambda(a x y)(+ a(* -0.1 s x)(* -0.3 s y)))
                                         p0 vec_x_onview vec_y_onview)
                               )
                         (mapcar '(lambda(p0 p1)(grdraw p0 p1 c))
                                 (list p p0 p0)(list p0 p1 p2))
                         )
                       p_close 4)
                      )
                    
                    )
                  ls_p_road)
               (setq p_ground nil);;closeしてないときは作成できない
               )
           )


         
         )
        
        ((= int_selectmenu int_selectmenu_ductedit)

         (if vnam_road
             ((lambda(ls_p p_close / p vec vec1 vec2 x y ang ang1 ang2)
                (if(setq vec_road(xvla-normal vnam_road p_close))
                    (progn
                      (setq vec(trans-x vec_road(list 0 0 1)vec_view)
                            ang(atan(cadr vec)(car vec))
                            ang(+ ang(* 0.9 pi))
                            vec1(list(cos ang)(sin ang)0.)
                            vec1(trans-x vec1 vec_view(list 0 0 1))
                            ang(+ ang(* 0.2 pi))
                            vec2(list(cos ang)(sin ang)0.)
                            vec2(trans-x vec2 vec_view(list 0 0 1))
                            )
                      (mapcar
                       '(lambda(v)
                          (grdraw p_close(mapcar '(lambda(a b)(+ a(* height_text 3. b)))p_close v) 3))
                       (list vec1 vec2))
                      ))
                )
              ls_p_road p_roadclick_temp)
           
           
           ((lambda(p c / s ls_p)
              (setq s(* height_text 0.8)
                    ls_p(mapcar
                         '(lambda(xx yy)
                            (mapcar '(lambda(a x y)(+ a(* xx x)(* yy y)))
                                    p vec_x_onview vec_y_onview)
                            )
                         (list s(- s)(- s)s) (list s(- s)s(- s)))
                    )
              (mapcar '(lambda(p0 p1)(grdraw p0 p1 c))
                      (list(car ls_p)(caddr ls_p))
                      (list(cadr ls_p)(cadddr ls_p)))
              )
            p_roadclick_temp 3)
           )

         (if(= int_inputdepth_temp 2)T
           ((lambda(p c / s ls_p p0 p1 p2)
              (setq s(* height_text 8.(if(= int_inputdepth_temp 0)1 -1))
                    p0(mapcar '+ p(list 0 0 s))
                    p1(mapcar '(lambda(a x y)(+ a(*  0.1 s x)(* -0.3 s y)))
                              p0 vec_x_onview vec_y_onview)
                    p2(mapcar '(lambda(a x y)(+ a(* -0.1 s x)(* -0.3 s y)))
                              p0 vec_x_onview vec_y_onview)
                    )
              (mapcar '(lambda(p0 p1)(grdraw p0 p1 c))
                      (list p p0 p0)(list p0 p1 p2))
              )
            p_roadclick_temp 4)
           )
         
         
         
         )
        ((and(null int_selectmenu)
             (or(and(= int_editdepth 0)
                    (= int_selectmenu_ductedit(func_selectmenu_ductedit_depth ls_guidemenu_page)))
                (and(= int_editdepth 1)
                    (= int_selectmenu_ductedit(func_selectmenu_ductedit_offset ls_guidemenu_page)))
                ))

         (setq int_selectmenu_ductedit -1
               p_ground p_roadclick_temp p_roadclick_temp nil
               p_click nil p_road nil
               int_grread 3)
         )
        ((and(null int_selectmenu)(= int_editdepth 1))
         (setq int_selectmenu_ductedit(func_selectmenu_ductedit_offset ls_guidemenu_page)
               int_selectmenu(func_selectmenu_ductedit_offset ls_guidemenu_page)
               bool_replacegrread T int_grread 2
               elem_grread(caar(nth int_selectmenu_ductedit ls_guidemenu))
               )
         )
        (T
         (setq int_selectmenu_ductedit nil
               p_roadclick_temp nil
               int_grread 5)

         )
        )
       
       ))

    (cons
     "CLICK"
     (lambda( / p_road  ls_arc bool vnam_insertany str_type);;(d- gr3_home()
       
       (if bool_firsttime_editduct
           (setq bool_firsttime_editduct
                 (if(< bool_firsttime_editduct 1)(1+ bool_firsttime_editduct))))

       (setq bool
             ((lambda(lst / a ls_nent bool entna str_height ls_current
                          entna_arc vnam_arc ls_currentarc p00 p01 p11 p10 vnam
                          num_line ii str_entselect vnam_select str_wholetype
                          
                          )
                (cond
                 
                 ((= int_ductmode 2) T)
                 (entna_depth nil)
                 (int_adddepth nil)
                 ;;insertarc から戻る合成クリックはここで無視するが、
                 ;;汎用クリック処理が拾った選択(管路自身の LINE 等)が
                 ;;ls_vnam_select に残ると、次の操作で経路選択(5458 付近)に
                 ;;誤って消費され vnam_road が管路の LINE になる。ここで捨てる
                 (bool_noeditdepth (setq ls_vnam_select nil))
                 (p_roadclick_temp nil)
                 ((or ls_exchangelevel ls_exchangedepth) nil)
                 
                 (p_click
                  
                  (setq vnam_insertduct nil ls_xdata nil)
                  (if(setq set_ent(ssget p_click ls_ssget))
                      (setq entna(ssname set_ent 0)
                            str_wholetype(cdr(assoc 0(entget entna)))
                            )
                    (setq entna nil str_wholetype nil )
                    )

                  (cond
                   ((= str_wholetype "INSERT")
                    (setq vnam_insertduct(vlax-ename->vla-object entna))
                    (vla-getXData vnam_insertduct "terraduct3d" 'array_Type 'array_Data )

                    (if array_data
                        (setq ls_xdata
                              (split_list 0(mapcar 'vlax-variant-value
                                                   (vlax-safearray->list array_data)))
                              str_type(cdr(assoc "terraduct3d" ls_xdata))
                              bool nil)
                      (if(setq set_ent(ssget p_click
                                             (list(cons -4 "<NOT")(cons 0 "INSERT")
                                                  (cons -4 "NOT>"))))
                          (setq entna(ssname set_ent 0)
                                bool nil vnam_insertduct nil
                                vnam_insertany(vlax-ename->vla-object entna) )
                        (setq bool nil vnam_insertduct nil
                              vnam_insertany  nil)
                        )
                      )
                    
                    )
                   
                   (T
                    
                    (setq ls_nent(nentselp p_click)
                          entna(car ls_nent)ls_nent(cdr ls_nent))
                    (if entna
                        (progn
                          (setq str_entselect(cdr(assoc 0(entget entna)))
                                vnam_select(vlax-ename->vla-object entna)
                                bool T)
                          
                          (while(and bool ls_nent)
                            (if(if(=(type(car ls_nent))'LIST)
                                   (=(type(caar ls_nent))'ENAME))
                                (setq ls_nent(car ls_nent)bool nil)
                              (setq ls_nent(cdr ls_nent)))
                            )
                          (if ls_nent T(setq ls_nent(list vnam_select)))
                          
                          ))
                    (setq bool nil)

                    
                    
                    (while lst
                      (setq ls_current(car lst)lst(cdr lst))

                      
                      (if(vl-position(cadr(assoc "OBJ" ls_current))ls_nent)
                          (cond
                           ((setq a(assoc "DEPTH" ls_current))
                            (setq entna_depth(cadr(assoc "OBJ" ls_current))
                                  vnam_depth(caddr(assoc "OBJ" ls_current))
                                  ;;int_duct(cadar ls_current)
                                  int_duct(cadr a)int_side(caddr a)
                                  vnam_line(cadr(assoc "OBJ"(assoc(list "LINE" int_duct)ls_vnam_duct)))

                                  ls_gcode(entget entna_depth)
                                  p_road(cdr(assoc 13 ls_gcode))
                                  p14(cdr(assoc 14 ls_gcode))

                                  height_temp
                                  (if(= int_inputdepth_temp 2)(caddr p14)
                                    (*(if(= int_inputdepth 1)1 -1)
                                      (-(caddr p_road)(caddr p14))))
                                  
                                  ;;vnam_road(cadr(assoc "ROAD" lst))
                                  lst nil)
                            
                            (if(= str_entselect "MTEXT")
                                (progn
                                  
                                  (setq str_height (as-numstr height_temp) )
                                  
                                  (settile_strinput
                                   'str_height nil
                                   (nth int_inputdepth_temp ls_type_inputdepth)nil )

                                  ;;(setq depth_duct(atof str_height)
                                        ;;p_road(cdr(assoc 13 ls_gcode))

                                  (setq p13
                                        (carxyz
                                         p14(if(= int_inputdepth_temp 2)
                                                (atof str_height)
                                              (+(caddr p_road)
                                                (*(if(= int_inputdepth 1)-1 1)
                                                  (atof str_height))))
                                         )
                                        ls_gcode(subst(cons 14 p13)(cons 14 p14)ls_gcode)
                                        ls_gcode(subst(cons 1(depth_level_str p_road p13))
                                                      (assoc 1 ls_gcode)ls_gcode)
                                        )
                                  
                                  (entmod ls_gcode)


                                  (if vnam_line
                                      ((if(= int_side 0)vla-put-startpoint vla-put-endpoint)
                                       vnam_line(vlax-3d-point p13)))
                                  
                                  (setq entna_depth nil
                                        bool_noeditdepth T
                                        bool nil )
                                  )
                              (progn
                                (if(setq vnam_road(cadr(assoc "ROAD" ls_current)))
                                    T
                                  (if(if(setq str_name(caddr(assoc "ROAD" ls_current)))
                                         (vl-catch-all-error-p
                                          (setq vnam(vl-catch-all-apply
                                                     'vla-Item
                                                     (list(vla-get-Blocks(vla-get-ActiveDocument(vlax-get-acad-object))) hand_road)
                                                     )))
                                       T)
                                      T
                                    (progn
                                      
                                      (vlax-for
                                       obj vnam
                                       "CENTER"
                                       (if(=(vla-get-ObjectName obj)"AcDb3dPolyline")
                                           (progn
                                             (setq obj
                                                   (vla-CopyObjects
                                                    (vla-get-ActiveDocument(vlax-get-acad-object))
                                                    (vlax-make-variant
                                                     (vlax-safearray-fill
                                                      (vlax-make-safearray vlax-vbObject (cons 0 0))
                                                      (list obj)))
                                                    (vla-get-ModelSpace
                                                     (vla-get-ActiveDocument(vlax-get-acad-object)))
                                                    )
                                                   vnam_road(car(vlax-safearray->list(vlax-variant-value obj)))
                                                   )
                                             (addkillobj vnam_road)
                                             ))
                                       )
                                      )))
                                
                                (setq depth_duct(atof(rtos height_temp 2 6)))
                                
                                (if(and vnam_road vnam_line)
                                    (setq offset_duct
                                          ((lambda( / vec p)
                                             (setq vec(carxyz
                                                       (mapcar '-(vlax-curve-getstartpoint vnam_line)
                                                               (vlax-curve-getendpoint vnam_line))
                                                       0)
                                                   vec(unit_vector vec)
                                                   vec(trans-x(list 1 0 0)vec(list 0 0 1))
                                                   p(vlax-curve-getclosestpointto vnam_road p_road nil)
                                                   )
                                             
                                             (atof(rtos(apply '+(mapcar '*(mapcar '- p p_road)vec))2 6))
                                             ))
                                          )
                                  )
                                
                                (setq bool T )
                                (vla-put-color vnam_depth 2)
                                
                                )
                              )
                            
                            )
                           ((setq ls_currentarc(assoc "ARC" ls_current))
                            (setq entna_arc(cadr(assoc "OBJ" ls_current))
                                  vnam_arc(caddr(assoc "OBJ" ls_current))
                                  lst nil)
                            
                            (if(= str_entselect "MTEXT")
                                (progn
                                  (setq str_radius(as-numstr(cdr(assoc "RADIUS" ls_current)))
                                        p_arcprev(caadr(assoc "POSITION" ls_current)))
                                  
                                  (settile_strinput
                                   'str_radius(lambda(str)(>(atof str)0))
                                   (mix_strasc(list 32076 36335 12398 26354 12370 21322 24452))
                                   (mix_strasc(list "0" 12424 12426 22823 12365 12356 20516 12434 20837 21147 12375 12390 12367 12384 12373 12356 ))
                                   )
                                  
                                  (setq rr(atof str_radius)
                                        bool nil
                                        bool_noeditdepth T
                                        ls_vnam_duct
                                        (subst(list ls_currentarc
                                                    (assoc "OBJ" ls_current)
                                                    (cons "RADIUS" rr)
                                                    (cons "POSITION" nil)
                                                    )
                                              ls_current ls_vnam_duct)
                                        
                                        )

                                  (if(=(caddr ls_currentarc)0)T
                                    ((lambda(lst)
                                       (setq ls_vnam_duct
                                             (subst(subst(cons "RADIUS" rr)(assoc "RADIUS" lst)lst)
                                                   lst ls_vnam_duct)
                                             )
                                       )
                                     (assoc(list "ARC"(cadr ls_currentarc)0)ls_vnam_duct)
                                     ))
                                  
                                  )
                              
                              (if(cdr(assoc "POSITION" ls_current))
                                  (progn
                                    
                                    (setq bool T )
                                    (vla-put-color vnam_arc 2)
                                    
                                    (setq ii(cadr ls_currentarc)
                                          vnam(cadr(assoc "OBJ"(assoc(list "LINE" ii)ls_vnam_duct)))
                                          p00(vlax-curve-getstartpoint vnam)
                                          p01(vlax-curve-getendpoint vnam)
                                          vnam(cadr(assoc "OBJ"(assoc(list "LINE"(1+ ii))ls_vnam_duct)))
                                          p10(vlax-curve-getstartpoint vnam)
                                          p11(vlax-curve-getendpoint vnam)

                                          ls_arcmove
                                          (cdr(connect_twist_curve
                                               (list nil p00 p01 p10 p11
                                                     (cdr(assoc "RADIUS" ls_current))length_arccenter)))

                                          ls_currentarc0(assoc(list "ARC" ii 0)ls_vnam_duct)
                                          ls_currentarc1(assoc(list "ARC" ii 1)ls_vnam_duct)
                                          str_edit "insertarc")

                                    )
                                (progn;;ここはとおらん
                                  (x-alert
                                   (list 20870 24359 12434 25375 12416 "2" 30452 32218 12364
                                         21516 19968 24179 38754 20869 12395 12394 12356 12392 12365 12399
                                         20870 24359 12398 20301 32622 12399 19968 24847 12395
                                         27770 23450 12373 12428 12414 12377
                                         "\n" 31227 21205 12391 12365 12414 12379 12435 ))
                                  ;;円弧を挟む2直線が同一平面内にないときは円弧の位置は一意に決定されます
                                  ;;移動できません
                                  
                                  (setq bool T)
                                  )
                                )
                              )

                            )
                           
                           ((setq num_line(cadr(assoc "LINE" ls_current)))
                            
                            (mapcar
                             '(lambda(lst)
                                (setq ls_vnam_duct(vl-remove lst ls_vnam_duct)
                                      lst(cdr(assoc "OBJ" lst))
                                      )
                                (mapcar
                                 '(lambda(vnam)
                                    (if(=(type vnam)'VLA-OBJECT)
                                        (progn
                                          (vla-delete vnam)
                                          (exckillobj vnam)
                                          ))
                                    )
                                 lst)
                                )
                             (list ls_current
                                   (assoc(list "DEPTH" num_line 0)ls_vnam_duct)
                                   (assoc(list "DEPTH" num_line 1)ls_vnam_duct)
                                   (assoc(list "ARC" num_line 0)ls_vnam_duct)
                                   (assoc(list "ARC" num_line 1)ls_vnam_duct))
                             )
                            
                            (while(setq lst(assoc(list "LINE"(setq num_line(1+ num_line)))
                                                 ls_vnam_duct))
                              (setq ls_vnam_duct
                                    (subst(subst(list "LINE"(1- num_line))
                                                (list "LINE" num_line)
                                                lst)
                                          lst ls_vnam_duct))
                              (mapcar
                               '(lambda(str i / lst)
                                  (if(setq lst(assoc(list str num_line i)ls_vnam_duct))
                                      (setq ls_vnam_duct
                                            (subst(subst(list str(1- num_line)i)
                                                        (list str num_line i)
                                                        lst)
                                                  lst ls_vnam_duct)))
                                  )
                               (list "DEPTH" "DEPTH" "ARC" "ARC")
                               (list 0 1 0 1))
                              )
                            
                            (setq int_max_duct(1- int_max_duct))
                            
                            (setq int_adddepth nil bool_noeditdepth T
                                  bool_replacegrread T int_grread 3 elem_grread(list 0 0 0)
                                  )
                            
                            (setq bool T)
                            )
                           )
                        )
                      )
                    
                    )
                   )
                  
                  
                  bool
                  
                  )
                 )
                )
              ls_vnam_duct)
             )


       ;; (if ls_exchangedepth
       ;;     (setq lst(car ls_exchangedepth)ls_exchangedepth(cdr ls_exchangedepth)
       ;;           entna_depth(car lst) p_road(cadr lst)
       ;;           depth_duct(caddr lst) int_duct(cadddr lst)
       ;;           bool_replacegrread(if ls_exchangedepth T)
       ;;           )
       ;;   )

       (cond
        (bool )

        ((if(or(= (cdr(assoc "terraduct3d" ls_xdata))"PROJECT")vnam_insertany)
             (progn
               (setq hand_road(vla-get-name vnam_insertduct)
                     vnam(vla-Item(vla-get-Blocks(vla-get-ActiveDocument(vlax-get-acad-object)))
                                  hand_road)
                     vnam_road_temp nil)
               
               (vlax-for
                obj vnam
                (if(if vnam_road_temp nil(=(vla-get-ObjectName obj)"AcDb3dPolyline"))
                    (progn 
                      (setq ls_p(vl-catch-all-apply 'vla-get-coordinates(list obj))
                            vnam_road_temp
                            (vla-Add3dPoly
                             (vla-get-ModelSpace(vla-get-ActiveDocument(vlax-get-acad-object)))
                             ls_p)
                            ls_vnam_killobj(cons vnam_road_temp ls_vnam_killobj)
                            )

                      (if(and(null ls_vnam_duct)(= int_getcolor_ductroad 0))
                          (progn
                            (setq int_colduct_temp(get_visual_color obj))
                            (vla-put-color vnam_road_temp int_colduct_temp)
                            
                            )
                        (vla-put-color vnam_road_temp(get_visual_color obj))
                        )
                      
                      )
                  )
                )
               
               (if vnam_road_temp
                   (setq vnam_road vnam_road_temp
                         ls_p_road(split_list 3(vlax-safearray->list(vlax-variant-value ls_p)))))
               
               )
           
           (if(if(setq vnam(car ls_vnam_select))
                  (progn
                    (setq ls_p(vl-catch-all-apply 'vla-get-coordinates(list vnam))
                          p0(vl-catch-all-apply 'vlax-curve-getstartpoint(list vnam))
                          p1(vl-catch-all-apply 'vlax-curve-getendpoint(list vnam))
                          ls_vnam_select nil )
                    (if(null(or(vl-catch-all-error-p p0)(vl-catch-all-error-p p1)))
                        (if(vl-position(vla-get-objectname vnam)(list "AeccDbSurfaceTin"))nil
                          (>(distance p0 p1)1e-8)))))
               (progn
                 (if(and(null ls_vnam_duct)(= int_getcolor_ductroad 0))
                     (progn
                       (setq int_colduct_temp(get_visual_color vnam))
                       ))
                 
                 (setq vnam_road vnam
                       hand_road(vla-get-handle vnam_road)
                       ls_p_road(if(vl-catch-all-error-p ls_p)(list p0 p1)
                                  (progn
                                    (setq ls_p(vlax-safearray->list(vlax-variant-value ls_p)))
                                    (if(=(vla-get-ObjectName vnam_road)"AcDbPolyline")
                                        (mapcar '(lambda(a)(carxyz a(vla-get-elevation vnam_road)))
                                                (split_list 2 ls_p))
                                      (split_list 3 ls_p))
                                    ))
                       )
                 )
             )
           )
         (setq int_ductdepth 0 bool_ductedit T  int_duct 0 int_selectmenu -1)
         
         )
        
        ((if int_adddepth
             (if(<(abs depth_duct)1e-8)
                 (progn;;深度の絶対値を0より大きくしてください
                   (x-alert(list 28145 24230 12398 32118 23550 20516 12434 "0" 12424 12426 22823 12365 12367 12375 12390 12367 12384 12373 12356 ))
                   T )
               (if(?(abs depth_duct)(* 2. radius_bend_temp))
                   (progn;;深度の絶対値を曲げ半径の2倍より小さくしてください
                     (x-alert(list 28145 24230 12398 32118 23550 20516 12434 26354 12370 21322 24452 12398 "2" 20493 12424 12426 23567 12373 12367 12375 12390 12367 12384 12373 12356 ))
                     T )
                 )))
         )
        
        ((if int_adddepth
             (if(setq set_ent(ssget "CP"(mapcar '(lambda(v / vec)
                                                   (setq vec(mapcar
                                                             '(lambda(x y)(* 0.4 height_text
                                                                             (+(*(car v)x)(*(cadr v)y))))
                                                             vec_x_onview vec_y_onview))
                                                   (mapcar '+ elem_grread vec)
                                                   )
                                                (list(list 1 1)(list 1 -1)(list -1 -1)(list -1 1))
                                                )
                                    (list(cons 0 "LINE"))))
                 (progn
                   (setq vnam_line(vlax-ename->vla-object(ssname set_ent 0)))
                   (null(apply 'or(mapcar
                                   '(lambda(lst / num)
                                      (if(setq num(vl-position(list "OBJ" vnam_line)lst))
                                          (setq num_line(cadr(assoc "LINE" lst))))
                                      )
                                   ls_vnam_duct)))
                   )
               T)
           )
         ;;選択対象ではありません/n管路の直線部を選択してください
         (x-alert(list 36984 25246 23550 35937 12391 12399 12354 12426 12414 12379 12435 "/n" 31649 36335 12398 30452 32218 37096 12434 36984 25246 12375 12390 12367 12384 12373 12356 ))
         )

        ((if ls_exchangelevel
             (if(setq set_ent(ssget elem_grread(list(cons 0 "DIMENSION")(list -3(list "terraduct3d")))))
                 ((lambda(lst / bool a b c)
                    (setq entna(ssname set_ent 0))
                    (while lst
                      (setq a(car lst)lst(cdr lst))
                      (if(if(setq c(assoc "DEPTH" a))(equal(cadr(setq b(assoc "OBJ" a)))entna))
                          (setq vnam(caddr b)int_duct(cadr c)int_side(caddr c)
                                lst nil bool T ))
                      )
                    bool
                    )
                  ls_vnam_duct)
               ))
         ((lambda(bool / f i)
            (if bool(setq f vl-remove i int_colductdimedit)(setq f cons i 2))
            (setq ls_exchangelevel(f(list entna vnam int_duct int_side)ls_exchangelevel))
            (if(= int_invisible_annotation 1)(vla-put-visible vnam :vlax-true))
            (vla-put-color vnam i)
            )
          (vl-position(list entna vnam int_duct int_side)ls_exchangelevel))
         
         )
        
        ((if ls_exchangelevel
             (if(setq set_ent(ssget elem_grread(list(cons 0 "INSERT")(list -3(list "terraduct3d")))))
                 ((lambda( / bool a ls_xdata)
                    (setq vnam(vlax-ename->vla-object(ssname set_ent 0)))
                    (vla-getXData vnam "terraduct3d" 'array_Type 'array_Data )
                    (if array_data
                        (setq ls_xdata
                              (split_list 0(mapcar 'vlax-variant-value
                                                   (vlax-safearray->list array_data)))
                              str_type(cdr(assoc "terraduct3d" ls_xdata)))
                      (setq str_type nil) )
                    (= str_type "PROJECT")
                    ) )
               ))

         (setq vnam_xroad nil)
         (vlax-for
          obj
          (vla-Item vnam_blocktable(vla-get-name vnam))
          (if vnam_xroad T
            (if(=(vla-get-ObjectName obj)"AcDb3dPolyline")
                (progn
                  (setq ls_p(vla-get-coordinates obj)
                        vnam_xroad
                        (vla-Add3dPoly
                         (vla-get-ModelSpace(vla-get-ActiveDocument(vlax-get-acad-object)))
                         ls_p)
                        )
                  (addkillobj vnam_xroad)
                  (setq ls_p(split_list 3(vlax-safearray->list(vlax-variant-value ls_p)))
                        ls_p(apply 'append(mapcar '(lambda(p)(carxyz p 0))ls_p))
                        array_p(vlax-make-safearray vlax-vbDouble(cons 0(1-(length ls_p)))))
                  (vlax-safearray-fill array_p ls_p)
                  (setq vnam_xroad_0(vla-Add3dPoly
                             (vla-get-ModelSpace(vla-get-ActiveDocument(vlax-get-acad-object)))
                             array_p))
                  (addkillobj vnam_xroad_0)
                  
                  )
              ))
          )

         
         ;; (setq ls_exchangedepth
         (mapcar
          '(lambda(lst / p13 p14 vec d entna i p_road j p_depth)
             (if(= int_invisible_annotation 1)(vla-put-visible(cadr lst):vlax-true))
             (vla-put-color(cadr lst)int_colductdimedit)
             (setq entna(car lst)i(caddr lst)j(cadddr lst)
                   ls_gcode(entget entna)
                   p13(cdr(assoc 13 ls_gcode))p14(cdr(assoc 14 ls_gcode))
                   d(-(caddr p13)(caddr p14))
                   vec(cdr(assoc 210 ls_gcode))
                   )
             (vla-put-startpoint vnam_cross_temp(vlax-3d-point(carxyz p13 0)))
             (vla-put-endpoint
              vnam_cross_temp (vlax-3d-point(mapcar '+ p13(list(-(cadr vec))(car vec)(-(caddr p13))))))
             (setq p_road(car(get_inters_point_vna vnam_xroad_0 vnam_cross_temp 01)))
             (vla-put-startpoint vnam_cross_temp(vlax-3d-point p_road))
             (vla-put-endpoint vnam_cross_temp(vlax-3d-point(carxyz p_road 1)))
             (setq p_road(car(get_inters_point_vna vnam_xroad vnam_cross_temp 01)))

             (setq str_level(depth_level_str p13 p14)
                   p_depth(mapcar '- p_road(list 0 0 d))
                   )
             
             (setq ls_gcode(subst(cons 13 p_road)(cons 13 p13)ls_gcode)
                   ls_gcode(subst(cons 14 p_depth)(cons 14 p14)ls_gcode)
                   ls_gcode(subst(cons 1 str_level)(assoc 1 ls_gcode)ls_gcode)
                   )
             (entmod ls_gcode)
             (setq lst(assoc(list "LINE" i)ls_vnam_duct)
                   vnam(cadr(assoc "OBJ" lst)))
             ((if(= j 0)vla-put-startpoint vla-put-endpoint)vnam(vlax-3d-point p_depth))
             
             (list entna p_road d i)
             )
          (vl-remove nil ls_exchangelevel))
         
         (setq ls_exchangelevel nil bool_replacegrread T bool_noeditdepth T)
         
         (mapcar '(lambda(v) (vla-delete v) (exckillobj v))
                 (list vnam_cross_temp vnam_xroad vnam_xroad_0))
         
         )
        (ls_exchangelevel)
        
        ((and int_adddepth num_line)
         (setq ps(vlax-curve-getstartpoint vnam_line)
               pe(vlax-curve-getendpoint vnam_line)

               ls_p0(mapcar '(lambda(d1 d2 b / p)
                               (setq p(mapcar '(lambda(a b)(+(* d1 a)(* d2 b)))ps pe))
                               (if b(mapcar '+ p(list 0 0 (- depth_duct)))p))
                            (list 0.7 0.6 0.4 0.3 0)(list 0.3 0.4 0.6 0.7 1.)(list nil T T nil nil))
               
               ls_p1(project_to_ground
                     ls_p0(list 0 0 1)(list str_lasground height_ground))

               entna(cadr(assoc "OBJ"(assoc(list "DEPTH" num_line 1)ls_vnam_duct)))
               vec_normal(cdr(assoc 210(entget entna)))
               
               ls_entna
               (mapcar '(lambda(p0 p1 / d str e vnam)
                          (setq d(apply '+(mapcar '* vec_normal p0))
                                str(depth_level_str p1 p0)
                                )
                          
                          (setq e(make_2pdimension
                                  entna(list p1 p0 vec_normal d
                                             nil(* 0.5 pi) 0. str str_dimstyle_ductlevel)))
                          
                          (if entna
                              (setq entna nil)
                            (progn
                              (setq vnam(vlax-ename->vla-object e))
                              (setq ls_p_dimtext(cons(cons vnam p0) ls_p_dimtext))
                              (vla-put-Arrowhead1Type vnam 13)
                              (vla-put-Arrowhead2Type vnam 6)
                              (vla-put-ExtLine1Suppress vnam -1)
                              (vla-put-ExtLine2Suppress vnam -1)
                              (if(= int_invisible_annotation 1)(vla-put-visible vnam :vlax-true))
                              (vla-put-color vnam int_colductdimedit)
                              (vla-put-HorizontalTextPosition vnam 3)
                              
                              (addkillobj vnam)
                              (list p0 e vnam)
                              )
                            )
                          )
                       ls_p0 ls_p1)
               ls_entna(cdr ls_entna)
               vnam(cadr(assoc "OBJ"(assoc(list "LINE" num_line)ls_vnam_duct)))
               
               )
         (vla-put-endpoint vnam(vlax-3d-point(car ls_p0)))

         (setq ls_vnam_duct
               (mapcar
                '(lambda(lst / str ls_num)
                   (setq ls_num(car lst)str(car ls_num))
                   (if(if(vl-position str(list "LINE" "DEPTH" "ARC"))
                          (>(cadr ls_num)num_line))
                       (subst(mapcar '(lambda(a b)(if b(+ 2 a)a))
                                     ls_num(list nil T nil))
                             ls_num lst)
                     lst)
                   )
                ls_vnam_duct)
               )

         (setq ps nil)
         (mapcar
          '(lambda(lst / p i)
             (setq p(car lst)lst(cdr lst))
             (if ps
                 (progn
                   (setq vnam_line
                         (vla-addline
                          (vla-get-modelspace(vla-get-activedocument(vlax-get-acad-object)))
                          (vlax-3d-point ps)(vlax-3d-point p))
                         ls_vnam_duct(cons(list(list "LINE" num_line)
                                               (list "OBJ" vnam_line))
                                          ls_vnam_duct)
                         ps nil i 1
                         )
                   (vla-put-color vnam_line int_colductdimedit)
                   (addkillobj vnam_line)
                   )
               (setq num_line(1+ num_line)ps p i 0)
               )
             
             (setq ls_vnam_duct
                   (cons(list(list "DEPTH" num_line i)
                             (cons "OBJ" lst)
                             (list "ROAD" vnam_road hand_road) )
                        ls_vnam_duct)
                   )
             )
          ls_entna)
         
         
         (setq int_adddepth nil bool_noeditdepth T int_max_duct(+ int_max_duct 2)
               int_editarcposition_temp 1
               bool_replacegrread T int_grread 3 elem_grread(list 0 0 0)
               )
         
         )
        
        ((if(and(vl-position int_ductdepth(list 0 1))bool_ductedit
                (< int_editdepth 2)
                (null vnam_insertany)(null vnam_insertduct))
             (if(or(= int_selectmenu_ductedit -1)entna_depth
                   bool_noeditdepth)
                 ;;(= str_editreturn "insertarc"))
                 nil
               (if p_roadclick_temp T
                 (setq p_roadclick_temp p_ground
                       bool_replacegrread T int_grread 2
                       int_selectmenu_ductedit(func_selectmenu_ductedit_depth ls_guidemenu_page)
                       elem_grread(caar(nth int_selectmenu_ductedit ls_guidemenu))
                       ))
               )
           )
         )
        
        ((or(and bool_ductedit
                 ;;(vl-position int_ductdepth(list 0 1));;切りたい
                 (null vnam_insertany)(null vnam_insertduct)
                 )
            
            (if(= int_bool_branch 1)
                (if(setq set_ent(ssget elem_grread(list(cons 0 "INSERT")(list -3(list "terraduct3d")))))
                    ((lambda( / vnam vnam0 vnma1 vnam2)
                       (setq vnam(vlax-ename->vla-object(ssname set_ent 0)))
                       (vla-getXData vnam "terraduct3d" 'array_Type 'array_Data )
                       (setq ls_xdata
                             (if array_data
                                 (split_list 0(mapcar 'vlax-variant-value
                                                      (vlax-safearray->list array_data))))
                             str_type(cdr(assoc "terraduct3d" ls_xdata))
                             )
                       (if(= str_type "DUCTBLOCK")
                           (progn
                             (setq str(vla-get-name vnam)
                                   vnam(vla-Item(vla-get-Blocks (vla-get-ActiveDocument(vlax-get-acad-object)))str)
                                   px nil
                                   )
                             
                             (vlax-for
                              obj vnam
                              
                              (if px T
                                (progn
                                  (vla-getXData obj "terraduct3d" 'array_Type 'array_Data )
                                  (setq ls_xdata
                                        (if array_data
                                            (split_list 0(mapcar 'vlax-variant-value
                                                                 (vlax-safearray->list array_data))))
                                        str_type(cdr(assoc "terraduct3d" ls_xdata))
                                        )
                                  
                                  (cond
                                   ((= str_type "CENTERLINE")
                                    (setq ls_p(vla-get-coordinates obj)
                                          vnam0(vla-Add3dPoly
                                                (vla-get-ModelSpace(vla-get-ActiveDocument(vlax-get-acad-object)))
                                                ls_p)
                                          ls_p(vlax-safearray->list(vlax-variant-value ls_p))
                                          ls_p(mapcar 'carxy(split_list 3 ls_p))
                                          ls_p(apply 'append ls_p)
                                          vnam1(xvla-lwpoly ls_p(list nil nil :vlax-false))
                                          ls_p(vlax-safearray->list(vlax-variant-value
                                                                    (vla-get-coordinates vnam_road)))
                                          ls_p(mapcar 'carxy(split_list 3 ls_p))
                                          ls_p(apply 'append ls_p)
                                          vnam2(xvla-lwpoly ls_p(list nil nil :vlax-false))
                                          px(car(get_inters_point_vna vnam1 vnam2 01))
                                          )
                                    (if px
                                        (progn
                                          (vla-put-startpoint vnam_cross_temp(vlax-3d-point px))
                                          (vla-put-endpoint vnam_cross_temp
                                                            (vlax-3d-point(mapcar '+ px(list 0 0 1))))
                                          (setq px(car(get_inters_point_vna vnam0 vnam_cross_temp 01))
                                                p_road(car(get_inters_point_vna
                                                           vnam_road vnam_cross_temp 01)))
                                          ))
                                    (mapcar 'vla-delete(list vnam0 vnam1 vnam2))
                                    
                                    )
                                   )
                                  ))
                              )
                             
                             
                             (if px
                                 (setq p_depth px )
                               )
                             
                             )))
                     ))
              )
            )
         
         (if int_selectmenu_ductedit(setq int_selectmenu_ductedit nil))
         (if(vl-position str_editreturn(list "insertarc" ))
             (setq str_editreturn "home"))
         
         (setq vec_normal(unit_vector(carxyz(if vec_road(mapcar '- vec_road)vec_view)0.))
               vec_x_offset(trans-x(list 1. 0. 0.)vec_normal(list 0 0 1)))

         (if bool_noeditdepth(setq bool_noeditdepth nil)
           (progn
             (if p_road T
               (setq p_road(mapcar '(lambda(a b)(+ a(* b offset_duct)))p_ground vec_x_offset)))

             
             (setq dist_normal(apply '+(mapcar '* vec_normal p_road)))
             (if(= int_bool_branch 1)T
               (setq p_depth(if(= int_inputdepth_temp 0)(mapcar '+ p_road(list 0. 0. depth_duct))
                              (if(= int_inputdepth_temp 1)(mapcar '- p_road(list 0. 0. depth_duct))
                                (if(= int_inputdepth_temp 2)(carxyz p_road depth_duct)
                                  )))
                     )
               )
             
             
             (setq str_level(depth_level_str p_road p_depth)
                   entna_depth(make_2pdimension
                               entna_depth(list p_road p_depth vec_normal dist_normal
                                                nil(* 0.5 pi) 0. str_level str_dimstyle_ductlevel))
                   )
             
             (if(vl-position entna_depth(mapcar '(lambda(a)(cadr(assoc "OBJ" a)))ls_vnam_duct))
                 (setq vnam_depth(vlax-ename->vla-object entna_depth))
               (progn
                 (setq int_ductend(if(= int_connecttype 0)int_min_duct int_max_duct)
                       int_searchnumber(if(= int_connecttype 0)0 1))
                 
                 ((lambda( / bool ii jj)
                    (setq bool T ii int_ductend int_duct ii)
                    (while bool
                      (if(assoc(list "DEPTH" ii(+ 0 int_searchnumber))ls_vnam_duct)
                          (if(assoc(list "DEPTH" ii(- 1 int_searchnumber))ls_vnam_duct)
                              (setq ii(+ ii(if(= int_connecttype 0)1 -1)))
                            (setq jj 1 bool nil))
                        (setq jj 0 bool nil))
                      )
                    (setq int_duct ii int_ductdepth jj)
                    ))
                 (if(= int_connecttype 0)
                     (setq int_max_duct(max int_duct int_max_duct))
                   (setq int_min_duct(min int_min_duct int_duct)))
                 
                 (setq vnam_depth(vlax-ename->vla-object entna_depth)
                       ls_vnam_duct(cons(list(list "DEPTH" int_duct int_ductdepth)
                                             (list "OBJ" entna_depth vnam_depth)
                                             (list "ROAD" vnam_road hand_road))
                                        ls_vnam_duct)
                       )
                 (setq ls_p_dimtext (cons(cons vnam_depth p_depth) ls_p_dimtext))
                 
                 (vla-put-Arrowhead1Type vnam_depth 13)
                 (vla-put-Arrowhead2Type vnam_depth 6)
                 (vla-put-ExtLine1Suppress vnam_depth -1)
                 (vla-put-ExtLine2Suppress vnam_depth -1)
                 (vla-put-HorizontalTextPosition vnam_depth 3)
                 
                 (addkillobj vnam_depth)
                 ))
             (if(= int_invisible_annotation 1)(vla-put-visible vnam_depth :vlax-true))
             (vla-put-color vnam_depth int_colductdimedit)
             
             (setq entna_depth nil)
             

             (if(and(setq entna0(cadr(assoc "OBJ"(assoc(list "DEPTH" int_duct 0)ls_vnam_duct))))
                    (setq entna1(cadr(assoc "OBJ"(assoc(list "DEPTH" int_duct 1)ls_vnam_duct)))))
                 (progn
                   (setq p0(vlax-3d-point(cdr(assoc 14(entget entna0))))
                         p1(vlax-3d-point(cdr(assoc 14(entget entna1)))))
                   (if(setq vnam_line(cadr(assoc "OBJ"(assoc(list "LINE" int_duct)ls_vnam_duct))))
                       (mapcar '(lambda(func p)(func vnam_line p))
                               (list vla-put-startpoint vla-put-endpoint)(list p0 p1))
                     (progn
                       (setq vnam_line
                             (vla-addline
                              (vla-get-modelspace(vla-get-activedocument(vlax-get-acad-object)))
                              p0 p1)
                             ls_vnam_duct(cons(list(list "LINE" int_duct)
                                                   (list "OBJ" vnam_line))
                                              ls_vnam_duct)
                             )
                       (vla-put-color vnam_line int_colductdimedit)
                       (addkillobj vnam_line)
                       )
                     )
                   )
               )
             ))
         
         (setq num_duct(- int_min_duct 2)
               ls_pmesh(list) ls_pbar(list) ls_center(list)ls_vec(list)
               p00 nil p01 nil p10 nil p11 nil vec0 nil vec1 nil
               ls_arc nil
               pitch_mesh(min pitch_project diam_duct_temp)
               )

         
         (if(<(abs pitch_mesh)1e-8)(setq pitch_mesh diam_duct_temp))

         (while(<=(setq num_duct(1+ num_duct))int_max_duct)
           (setq vnam_line0(cadr(assoc "OBJ"(assoc(list "LINE" num_duct)ls_vnam_duct)))
                 vnam_line1(cadr(assoc "OBJ"(assoc(list "LINE"(1+ num_duct))ls_vnam_duct))))
           
           (if vnam_line0(setq p00 p10 p01 p11))
           (if vnam_line1
               (setq p10(vlax-curve-getstartpoint vnam_line1)
                     p11(vlax-curve-getendpoint vnam_line1)
                     ))
           (cond
            ((and vnam_line0 vnam_line1))
            (vnam_line0;;初回限定
             (setq lst(car ls_pbar)p(car lst))
             (if(<(apply '+(mapcar '*(mapcar '- p01 p)(caddr lst)))-1e-8)
                 T
               (progn
                 (setq vec0(unit_vector(mapcar '- p01 p00)));;これでいいとは思うがp01-pでもいい
                 ;; (if(= int_protectcon_temp 2)T
                 ((lambda( / d n i dd pm)
                    (setq d(distance p p01) n(1+(fix(/ d pitch_mesh))) d(/ d n)
                          dd(- d))
                    (if(< d 1e-8)(setq ls_pmesh(cons(list p vec0)ls_pmesh))
                      (while(>=(setq n(1- n))-1)
                        (setq dd(+ dd d)
                              pm(mapcar '(lambda(a b)(+ a(* dd b)))p vec0)
                              ls_pmesh(cons(list pm vec0)ls_pmesh)
                              )
                        )
                      )
                    ))
                 ;;)
                 
                 (setq ls_pbar(cons(list p01 nil vec0) ls_pbar))
                 ))
             
             )
            (vnam_line1;;最終回限定
             (setq ls_pbar(cons(list p10 nil(unit_vector(mapcar '- p11 p10)))
                               ls_pbar))
             )
            )
           

           ;; (if(if(and vnam_line0 vnam_line1 )
           ;;        (if(or(= num_duct int_duct)(=(1+ num_duct)int_duct))
           ;;            (progn
                        
           ;;              ;;todo不要か
           ;;              nil)
           ;;          T)
           ;;      T)
           ;;     (progn
           ;;       T
           ;;       )

           (if(and vnam_line0 vnam_line1 )
               (progn

                 (if(setq ls_currentarc0(assoc(list "ARC" num_duct 0)ls_vnam_duct))T
                   (setq ls_currentarc0(list(list "ARC" num_duct 0)(list "OBJ" )
                                            (cons "RADIUS" radius_bend_temp)
                                            (cons "POSITION" nil) )
                         ))
                 (if(setq ls_currentarc1(assoc(list "ARC" num_duct 1)ls_vnam_duct))T
                   (setq ls_currentarc1(list(list "ARC" num_duct 1)(list "OBJ" )
                                            (cons "RADIUS" radius_bend_temp)
                                            (cons "POSITION" nil))
                         ls_vnam_duct(cons ls_currentarc1(cons ls_currentarc0 ls_vnam_duct))
                         ))
                 
                 
                 (setq rr(cdr(assoc "RADIUS" ls_currentarc0)))

                 (setq ls_arc(connect_twist_curve ;;(list vec_normal pc p0 p1 p2 length_straight)
                              (list p00 p01 p10 p11 rr length_arccenter
                                    ((lambda( / lst px0 px1 vec)
                                       (setq lst(cdr(assoc "POSITION" ls_currentarc0)))
                                       ;;(setq px0(cadar lst)px1(caddr(car lst)))
                                       ;; (if(if(and px0 px1)
                                       ;;        (and
                                       ;;         (<(distance(list 0 0 0)
                                       ;;                    (cross_product
                                       ;;                     (unit_vector(mapcar '- p01 p00))
                                       ;;                     (unit_vector(mapcar '- px0 p00))))1e-8)
                                       ;;         (<(distance(list 0 0 0)
                                       ;;                    (cross_product
                                       ;;                     (unit_vector(mapcar '- p11 p10))
                                       ;;                     (unit_vector(mapcar '- px1 p10))))1e-8)
                                       ;;         ))
                                       ;;     lst
                                       ;;   (progn
                                       ;;     (setq int_editarcposition_temp 1)
                                       ;;     nil
                                       ;;     )
                                       ;;)
                                       lst ))
                                    (strcat(itoa num_duct)"-"(itoa(1+ num_duct))":")))
                       )


                 (if(= int_editarcradius 0)
                     (setq int_editarcposition_temp 3 delta_arcmove(* 0.1 radius_bend_temp)))
                 (if(=(car ls_arc)"BREAK")
                     (if(cdr ls_arc)
                         (setq num_duct(1+ int_max_duct)
                               bool_arcfirsttime
                               (or(/= int_editarcposition 0)
                                  int_editarcposition_temp)
                               
                               ls_arcmove(cdr ls_arc)
                               str_edit "insertarc")
                       (setq num_duct(1+ int_max_duct)
                             
                             ;; bool_replacegrread T
                             ;; int_grread 2 elem_grread 8
                             )
                       )
                   
                   (mapcar
                    '(lambda(ls_current lst / e vnam vec_normal pc p0 p1 p2 length_straight e_out)
                       (mapcar 'set '(pc p0 p1 p2 vec_normal length_straight)lst)
                       
                       (setq e(cadr(assoc "OBJ" ls_current))
                             dist_normal(apply '+(mapcar '* pc vec_normal))
                             e_out
                             (make_arcdimension
                              e(list pc p0 p1 p2 rr vec_normal dist_normal
                                     (arc2_dimtext rr p1 p2)
                                     str_dimstyle_ductlevel))
                             )
                       
                       
                       (if e
                           (setq ls_vnam_duct
                                 (subst(list(assoc "ARC" ls_current)
                                            (assoc "OBJ" ls_current)
                                            (cons "RADIUS" rr)
                                            (assoc "POSITION" ls_current)
                                            )
                                       ls_current ls_vnam_duct)
                                 vnam(caddr(assoc "OBJ" ls_current))
                                 )
                         (progn
                           (setq vnam(vlax-ename->vla-object e_out)
                                 ls_vnam_duct
                                 (subst(list(assoc "ARC" ls_current)
                                            (list "OBJ" e_out vnam)
                                            (cons "RADIUS" rr)
                                            
                                            (assoc "POSITION" ls_current)
                                            )
                                       ls_current ls_vnam_duct)
                                 )
                           
                           (setq ls_p_dimtext (cons(cons vnam p2) ls_p_dimtext))
                           
                           (arc2_dimstyle vnam)
                           (addkillobj vnam)
                           ))
                       (if(= int_invisible_annotation 1)(vla-put-visible vnam :vlax-true))
                       (vla-put-color vnam int_colductdimedit)

                       e_out)
                    (list ls_currentarc0 ls_currentarc1)ls_arc)
                   )

                 ))
           
           
           (mapcar
            '(lambda(i)
               (if(if(setq entna(cadr(assoc "OBJ"(assoc(list "ARC" num_duct i)ls_vnam_duct))))
                      (progn
                        (setq p(caar ls_pbar)
                              ls_gcode(entget entna) p15(cdr(assoc 15 ls_gcode))
                              p13(cdr(assoc 13 ls_gcode))p14(cdr(assoc 14 ls_gcode))
                              )
                        (>(distance p13 p14)1e-8)
                        ))
                   (progn
                     (setq vec_normal(cdr(assoc 210 ls_gcode))
                           vec13(mapcar '- p13 p15)rr(distance p15 p13)
                           vec14(mapcar '- p14 p15)
                           vec13(mapcar '(lambda(a)(/ a rr))vec13)
                           vec14(mapcar '(lambda(a)(/ a rr))vec14)
                           vec0(cross_product vec_normal vec13)
                           vec1(cross_product vec_normal vec14)
                           )
                     (if(<(apply '+(mapcar '* vec0 vec14))0)(setq vec0(mapcar '- vec0)))
                     (if(>(apply '+(mapcar '* vec1 vec13))0)(setq vec1(mapcar '- vec1)))
                     (if(<(apply '+(mapcar '*(mapcar '- p13 p)vec0))-1e-8)
                         (setq ls_pbar(cons(list p13 nil vec0)(cdr ls_pbar)))
                       ;; (if(= int_protectcon_temp 2)T
                       ((lambda(p / d n i dd pm)
                          (setq d(distance p p13) n(1+(fix(/ d pitch_mesh))) d(/ d n)
                                dd(- d))
                          (while(>(setq n(1- n))-1)
                            (setq dd(+ dd d)
                                  pm(mapcar '(lambda(a b)(+ a(* dd b)))p vec0)
                                  ls_pmesh(cons(list pm vec0)ls_pmesh)
                                  )
                            )
                          )
                        p)
                       ;; )
                       )

                     (if(<(distance(caar ls_pbar)p13)1e-8)(setq ls_pbar(cdr ls_pbar)))
                     (setq ls_pbar(cons(list p13 p15 vec0)ls_pbar)
                           ls_pbar(cons(list p14 nil vec1)ls_pbar)
                           )
                     
                     ;; (if(= int_protectcon_temp 2)T
                     ((lambda( / d n i ang r vec_x vec_y pm dd c s v)
                        (setq ang(atan(distance(cross_product vec13 vec14)(list 0 0 0))
                                      (apply '+(mapcar '* vec13 vec14)))
                              vec_x(mapcar '(lambda(a)(* a rr))vec13)
                              vec_y(mapcar '(lambda(a)(* a rr))vec0)
                              d(* rr ang) n(1+(fix(/ d(min(* 0.5 rr) pitch_mesh))))
                              d(/ ang n)
                              ang 0)
                        
                        (while(>(setq n(1- n))0)
                          (setq ang(+ ang d)c(cos ang)s(sin ang)
                                v(mapcar '(lambda(x y)(+ (* -1 s x)(* c y)))vec13 vec0)
                                pm(mapcar '(lambda(a x y)(+ a(* c x)(* s y)))p15 vec_x vec_y)
                                ls_pmesh(cons(list pm v)ls_pmesh)
                                )
                          )
                        ))
                     ;; )
                     
                     
                     
                     ))
               )
            (if(=(car ls_arc)"BREAK")nil(list 0 1)))
           
           );;ARC
         (if(= str_edit "insertarc")T(setq int_editarcposition_temp nil))

         
         (if(if ls_arc(=(car ls_arc)"BREAK"))nil
           (progn

             (setq ls_pcenterline(mapcar 'car(reverse ls_pmesh)))
             
             (if(setq lst(assoc(list "SOLID" 0)ls_vnam_duct))
                 (progn
                   (setq vnam(cadr(assoc "OBJ" lst))
                         ls_vnam_duct(vl-remove lst ls_vnam_duct))
                   (vla-delete vnam)
                   (exckillobj vnam)
                   ))
             
             (if(and(= int_ductsolidmesh 1)ls_pbar)
                 (progn
                   (setq ls_pbar(reverse ls_pbar)
                         entna(bendpipe_lwpsld
                               (* 0.5 diam_duct_temp) ls_pbar (getvar "CLAYER") nil)
                         vnam(vlax-ename->vla-object entna)
                         ls_vnam_duct(cons(list(list "SOLID" 0)(list "OBJ" vnam)
                                               (cons "DIAM" diam_duct_temp) )
                                          ls_vnam_duct)
                         
                         )
                   (vla-put-color vnam int_colduct_temp)
                   (if(= int_hidesolid 1)(vla-put-visible vnam :vlax-false))
                   
                   (addkillobj vnam)
                   
                   )
               (if ls_pmesh
                   (progn
                     
                     (setq numy 32
                           ls_intmesh(inclist 0 numy)
                           ang_d(/(* 2. pi)numy)
                           r(* 0.5 diam_duct_temp)
                           vecxp nil vecyp nil
                           )
                     
                     (setq ls_pduct
                           (mapcar
                            '(lambda(lst / p v vecx vecy)
                               (setq p(car lst)v(cadr lst)
                                     v(unit_vector v )
                                     vecx(trans-x(list 1 0 0)v(list 0 0 1))
                                     vecy(trans-x(list 0 1 0)v(list 0 0 1))
                                     )
                               
                               (if(if vecxp(>(apply '+(mapcar '* vecx vecxp))0)T)T
                                 (setq vecx vecxp))
                               (setq vecxp vecx)
                               (if(<(caddr vecy)0)(setq vecy(mapcar '- vecy)))
                               (mapcar '(lambda(i / c s)
                                          (setq c(cos(* ang_d i))s(sin(* ang_d i)))
                                          (mapcar '(lambda(a x y)(+(* r c x)(* r s y)a))
                                                  p vecx vecy))
                                       ls_intmesh)
                               )
                            (reverse ls_pmesh)
                            )
                           
                           numx(length ls_pduct)
                           ls_p(apply 'append(apply 'append ls_pduct))
                           )
                     
                     (setq array_mesh(vlax-make-safearray vlax-vbDouble(cons 0(1-(length ls_p)))))
                     (vlax-safearray-fill array_mesh ls_p)
                     (setq vnam
                           (vla-Add3DMesh
                            (vla-get-ModelSpace(vla-get-ActiveDocument (vlax-get-acad-object)))
                            numx numy array_mesh)

                           ls_vnam_duct(cons(list(list "SOLID" 0)(list "OBJ" vnam)
                                                 (cons "DIAM" diam_duct_temp) )
                                            ls_vnam_duct)
                           
                           )
                     (vla-put-color vnam int_colduct_temp)
                     (vla-put-nclose vnam :vlax-true)
                     (if(= int_hidesolid 1)(vla-put-visible vnam :vlax-false))
                     
                     (addkillobj vnam)

                     )
                 )
               )
             
             (if(setq lst(assoc(list "MESH" 0)ls_vnam_duct))
                 (progn
                   (setq vnam(cadr(assoc "OBJ" lst))
                         ls_vnam_duct(vl-remove lst ls_vnam_duct))
                   (vla-delete vnam)
                   (exckillobj vnam)
                   ))

             
             (if(if(= int_protectcon_temp 2)nil ls_pmesh)
                 (progn
                   (setq numy(if(= int_protectcon_temp 0)
                                 (if(= filet_protect_temp 0.)4 8)
                               (if(= int_protectcon_temp 1)
                                   (if(= filet_protect_temp 0.)-4 -6)
                                 ))
                         int_corner numy
                         
                         w(* 0.5 width_protect_temp)
                         h(* 0.5 height_protect_temp)
                         f filet_protect_temp
                         
                         ls_pmesh
                         (mapcar
                          '(lambda(lst / p v vecx vecy)
                             (setq p(car lst)v(cadr lst)
                                   v(unit_vector(carxyz v 0.))
                                   vecx(trans-x(list 1 0 0)v(list 0 0 1))
                                   vecy(trans-x(list 0 1 0)v(list 0 0 1))
                                   )
                             
                             (vl-remove
                              nil
                              (mapcar '(lambda(lst / bool iw iwf ih ihf)
                                         (mapcar 'set '(bool iw iwf ih ihf)lst)
                                         (if(vl-position numy bool)
                                             (mapcar '(lambda(a x y)(+(*(+(* iw w)(* iwf f))x)
                                                                      (*(+(* ih h)(* ihf f))y) a))
                                                     p vecx vecy))
                                         )
                                      (list(list(list 8 4)-1  1 1 0)
                                           (list(list 8)  -1  0 1 -1)
                                           (list(list -6 -4)-1 0 0 0)
                                           (list(list 8 4 -6 -4)-1 0 -1 1)
                                           (list(list 8 -6)-1  1 -1 0)
                                           (list(list 8 -6) 1 -1 -1 0)
                                           (list(list 8 4 -6 -4) 1 0 -1 1)
                                           (list(list -6 -4) 1 0 0 0)
                                           (list(list 8)   1  0 1 -1)
                                           (list(list 8 4) 1 -1 1 0)
                                           ))
                              )
                             )
                          (reverse ls_pmesh)
                          )
                         
                         numx(length ls_pmesh)
                         numy(abs numy)
                         ls_p(apply 'append(apply 'append ls_pmesh))
                         )
                   
                   (setq array_mesh(vlax-make-safearray vlax-vbDouble(cons 0(1-(length ls_p)))))
                   (vlax-safearray-fill array_mesh ls_p)
                   (setq vnam
                         (vla-Add3DMesh
                          (vla-get-ModelSpace(vla-get-ActiveDocument (vlax-get-acad-object)))
                          numx numy array_mesh)
                         ls_vnam_duct(cons(list(list "MESH" 0)(list "OBJ" vnam)
                                               (cons "CORNER" int_corner)
                                               (cons "WIDTH" width_protect_temp)
                                               (cons "HEIGHT" height_protect_temp)
                                               (cons "FILET"  filet_protect_temp)
                                               )
                                          ls_vnam_duct)
                         )

                   (vla-put-layer vnam str_layprotect)
                   (vla-put-color vnam int_colprotect)
                   (vla-put-nclose vnam :vlax-true)
                   (if(= int_hidesolid 1)(vla-put-visible vnam :vlax-false))
                   
                   (addkillobj vnam)
                   
                   ))
             ))
         


         (if(= int_bool_branch 1)(setq int_bool_branch 0))
         (if(= int_editstatus 2)
             (setq bool_replacegrread T int_grread 2 elem_grread 13))

         )

        ;;editmode
        ((and(null ls_vnam_duct)
             vnam_insertduct(= str_type "DUCTBLOCK"))
         
         (setq str(vla-get-name vnam_insertduct)
               vnam(vla-Item(vla-get-Blocks (vla-get-ActiveDocument(vlax-get-acad-object)))str)
               ls_search(list)num_min nil num_max nil
               int_protectcon_temp 2
               int_editstatus
               (if(and(= int_ductmode 1)(= depth_duct 0.)(= offset_duct 0.))1
                 (if(= int_ductmode 1)2 0))
               )
         
         (if(= int_editstatus 2)
             (progn
               (setq str "DUCT$" i 0 bool T)
               (while bool
                 (setq i(1+ i)
                       str_ductname(strcat str(substr(itoa(+ 1000 i))2))
                       bool
                       (null
                        (vl-catch-all-error-p
                         (vl-catch-all-apply 'vla-Item(list vnam_blocktable str_ductname))))
                       )
                 )
               )
           (setq str_ductname str))
         

         (vlax-for
          obj vnam
          (vla-getXData obj "terraduct3d" 'array_Type 'array_Data )
          (setq ls_xdata
                (if array_data
                    (split_list 0(mapcar 'vlax-variant-value
                                         (vlax-safearray->list array_data))))
                str_type(cdr(assoc "terraduct3d" ls_xdata))
                )
          (cond
           ((or(= str_type "DEPTH")(= str_type "ARC"))
            (setq num(cdr(assoc "NUM" ls_xdata))
                  int_side(cdr(assoc "SIDE" ls_xdata))
                  )
            (if num_min(setq num_min(min num_min num)num_max(max num_max num))
              (setq num_min num num_max num))
            (setq lst(cons(list str_type num int_side)
                          (cons(cons "OBJ" obj)
                               ls_xdata))
                  ls_search(cons lst ls_search))
            )
           ((= int_editstatus 1))
           
           ((= str_type "DUCTSOLID")
            (setq diam_duct_temp(cdr(assoc "DIAM" ls_xdata))
                  int_colduct_temp(vla-get-color obj)
                  )
            )
           ((= str_type "CONMESH")
            (setq int_protectcon_temp
                  (if(<(cdr(assoc "CORNER" ls_xdata))0)1 0)
                  width_protect_temp(cdr(assoc "WIDTH" ls_xdata))
                  height_protect_temp(cdr(assoc "HEIGHT" ls_xdata))
                  filet_protect_temp(cdr(assoc "FILET" ls_xdata))
                  )
            )
           )
          )

         (setq int_min_duct 0 int_max_duct(- num_max num_min)
               num_min(1- num_min) ls_vnam_duct(list)
               vnam_currentinsert vnam_insertduct
               vnam_insertduct nil vnam_road nil
               ls_line(list)
               ls_roadfrominsert(list)
               num_temp num_min
               )
         
         (while(<=(setq num_temp(1+ num_temp))num_max)
           (setq ls_p
                 (mapcar
                  '(lambda(int_side / ls_gcode)
                     (setq lst(assoc(list "DEPTH" num_temp int_side)ls_search)
                           ls_search(vl-remove lst ls_search)
                           vnam_road
                           ((lambda(hand_road / entna_road vnam str int_col)
                              (if(setq vnam
                                       ((lambda(h / block v)
                                          (if h T(setq h ""))
                                          (if(vl-catch-all-error-p
                                              (setq block(vl-catch-all-apply 'vla-Item(list vnam_blocktable h))))
                                              nil
                                            (vlax-for
                                             obj block
                                             (if entna_road T
                                               (if(=(vla-get-ObjectName obj)"AcDb3dPolyline")
                                                   (setq entna_road(vlax-vla-object->ename obj)
                                                         v obj
                                                         ))
                                               )
                                             )
                                            )
                                          
                                          (if entna_road T
                                            (if(setq entna_road(handent h))
                                                (setq v(vlax-ename->vla-object entna_road))))
                                          v
                                          )
                                        hand_road)
                                       )
                                  (if(progn
                                       (setq str(cdr(assoc 2(entget(cdr(assoc 330(entget entna_road)))))))
                                       (vl-position str(list "*Model_Space" "*Paper_Space"))
                                       )
                                      T
                                    (if(vl-position vnam ls_roadfrominsert)T
                                      (progn
                                        
                                        (setq ls_roadfrominsert(cons vnam ls_roadfrominsert)
                                              int_col(get_visual_color vnam)
                                              vnam
                                              (vla-CopyObjects
                                               (vla-get-ActiveDocument(vlax-get-acad-object))
                                               (vlax-make-variant
                                                (vlax-safearray-fill
                                                 (vlax-make-safearray vlax-vbObject (cons 0 0))
                                                 (list vnam)))
                                               (vla-get-ModelSpace
                                                (vla-get-ActiveDocument(vlax-get-acad-object)))
                                               )
                                              vnam(car(vlax-safearray->list(vlax-variant-value vnam)))
                                              )
                                        (addkillobj vnam)
                                        (vla-put-color vnam int_col)
                                        ))
                                    ) )
                              vnam)
                            (cdr(assoc "ROAD" lst)))
                           
                           vnam(cdr(assoc "OBJ" lst))
                           vnam
                           (vla-CopyObjects
                            (vla-get-ActiveDocument(vlax-get-acad-object))
                            (vlax-make-variant
                             (vlax-safearray-fill
                              (vlax-make-safearray vlax-vbObject (cons 0 0))
                              (list vnam)))
                            (vla-get-ModelSpace(vla-get-ActiveDocument(vlax-get-acad-object)))
                            )
                           vnam(car(vlax-safearray->list(vlax-variant-value vnam)))
                           entna(vlax-vla-object->ename vnam)
                           lst(cdr(assoc 14(entget entna)))
                           ls_p_dimtext(cons(cons vnam lst)ls_p_dimtext)
                           )
                     
                     ;; (if(or str_lasground height_ground)
                     ;;     ((lambda( / p13 p14 lst v pp13 pp14 str)
                     ;;        (setq lst(entget entna)
                     ;;              p13(cdr(assoc 13 lst))p14(cdr(assoc 14 lst))
                     ;;              pp13(car(project_to_ground
                     ;;                       (list p13)(list 0 0 1)(list str_lasground height_ground)))
                     ;;              pp14(mapcar '+ pp13(mapcar '- p14 p13))
                     ;;              str(strcat "GL"(if(<(-(caddr pp14)(caddr pp13))0)"-" "+")"<>\\P"
                     ;;                         "EL = "(rtos(caddr pp14)2 int_unitelevation))
                     ;;              lst(subst(cons 13 pp13)(cons 13 p13)lst)
                     ;;              lst(subst(cons 14 pp14)(cons 14 p14)lst)
                     ;;              lst(subst(cons 1 str)(assoc 1 lst)lst)
                     ;;              )
                     ;;        (entmod lst)
                     ;;        ))
                     ;;   )
                     
                     (setq ls_vnam_duct(cons(list(list "DEPTH" num_temp int_side)
                                                 (list "OBJ" entna vnam)
                                                 (list "ROAD" vnam_road hand_road) )
                                            ls_vnam_duct)
                           )
                     (if(= int_invisible_annotation 1)(vla-put-visible vnam :vlax-true))
                     (vla-put-color vnam int_colductdimedit)
                     (addkillobj vnam)

                     (if(= int_editstatus 2)
                         (if(= int_side 0)
                             (setq vnam0 vnam entna0 entna)
                           (setq vnam1 vnam entna1 entna)))
                     
                     (cdr(assoc 14 (entget entna)))
                     )
                  (list 0 1))

                 p00(car ls_p)p01(cadr ls_p)
                 
                 )
           
           (if(= int_editstatus 2)
               (progn
                 (setq vec(unit_vector(carxyz(mapcar '- p00 p01)0))
                       vec_offset(trans-x(list 1 0 0)vec(list 0 0 1))
                      vec_offset
                       (mapcar '(lambda(x y)(+(* offset_duct x)(* depth_duct y)))
                               vec_offset(list 0 0(if(= int_inputdepth_temp 1)-1 1)))
                       p10(mapcar '+ p00 vec_offset)
                       p11(mapcar '+ p01 vec_offset)
                       ls_line(cons(list p00 p01 p10 p11)ls_line)
                       )
                 
                 (mapcar
                  '(lambda(vnam entna)
                     (vla-Move vnam(vlax-3d-point 0 0 0)(vlax-3d-point vec_offset))
                     (setq ls_gcode(entget entna))
                     (if(setq p(car(project_to_ground
                                    (list(cdr(assoc 13 ls_gcode)))(list 0 0 1)
                                    (list str_lasground height_ground))))
                         (entmod(subst(cons 13 p)(assoc 13 ls_gcode)ls_gcode)))
                     )
                  (list vnam0 vnam1)(list entna0 entna1))
                 
                 )
             (setq p10 p00 p11 p01))

           ;;todo
           (setq vnam
                 (vla-addline
                  (vla-get-modelspace(vla-get-activedocument(vlax-get-acad-object)))
                  (vlax-3d-point p10)(vlax-3d-point p11))
                 ls_vnam_duct(cons(list(list "LINE" num_temp)
                                       (list "OBJ" vnam))
                                  ls_vnam_duct)
                 )
           (addkillobj vnam)

           (if(setq lst(assoc(list "ARC"(1- num_temp)0)ls_search))
               ((lambda( / ls_gcode ls_p0 ls_p1 rr entna0 entna1)
                  (setq ls_search(vl-remove lst ls_search)
                        rr(cdr(assoc "RADIUS" lst))
                        vnam(cdr(assoc "OBJ" lst))
                        vnam
                        (vla-CopyObjects
                         (vla-get-ActiveDocument(vlax-get-acad-object))
                         (vlax-make-variant
                          (vlax-safearray-fill
                           (vlax-make-safearray vlax-vbObject (cons 0 0))
                           (list vnam)))
                         (vla-get-ModelSpace(vla-get-ActiveDocument(vlax-get-acad-object)))
                         )
                        vnam(car(vlax-safearray->list(vlax-variant-value vnam)))
                        entna0(vlax-vla-object->ename vnam)

                        lst(cdr(assoc 10(entget entna0)))
                        ls_p_dimtext(cons(cons vnam lst)ls_p_dimtext)
                        
                        ls_gcode(entget entna0)
                        ls_p0
                        ((lambda( / pc p0 p1 p2)
                           (setq pc(cdr(assoc 15 ls_gcode))
                                 p0(cdr(assoc 13 ls_gcode))p1(cdr(assoc 14 ls_gcode))
                                 p2(mapcar '(lambda(a b)(+ a(* rr b)))
                                           pc(unit_vector(mapcar '(lambda(a b c)(+ a b(* -2 c)))
                                                                 p0 p1 pc)))
                                 )
                           (list pc p0 p1 p2)
                           ))


                        lst(assoc(list "ARC"(1- num_temp)1)ls_search)
                        ls_search(vl-remove lst ls_search)
                        vnam(cdr(assoc "OBJ" lst))
                        vnam
                        (vla-CopyObjects
                         (vla-get-ActiveDocument(vlax-get-acad-object))
                         (vlax-make-variant
                          (vlax-safearray-fill
                           (vlax-make-safearray vlax-vbObject (cons 0 0))
                           (list vnam)))
                         (vla-get-ModelSpace(vla-get-ActiveDocument(vlax-get-acad-object)))
                         )
                        vnam(car(vlax-safearray->list(vlax-variant-value vnam)))
                        entna1(vlax-vla-object->ename vnam)

                        lst(cdr(assoc 10(entget entna1)))
                        ls_p_dimtext(cons(cons vnam lst)ls_p_dimtext)
                        
                        ls_gcode(entget entna1)
                        ls_p1
                        ((lambda( / pc p0 p1 p2)
                           (setq pc(cdr(assoc 15 ls_gcode))
                                 p0(cdr(assoc 13 ls_gcode))p1(cdr(assoc 14 ls_gcode))
                                 p2(mapcar '(lambda(a b)(+ a(* rr b)))
                                           pc(unit_vector(mapcar '(lambda(a b c)(+ a b(* -2 c)))
                                                                 p0 p1 pc)))
                                 )
                           (list pc p0 p1 p2)
                           ))
                        )

                  (if(= int_editstatus 2)
                      ((lambda( / p00 p01 p10 p11 p02 p03 p12 p13 lst px0 px1 vec0 vec1 veco)
                         (mapcar 'set '(p00 p01 p10 p11)(cadr ls_line))
                         (mapcar 'set '(p02 p03 p12 p13)(car ls_line))
                         (setq vec0(unit_vector(mapcar '- p01 p00))
                               vec1(unit_vector(mapcar '- p03 p02))
                               veco
                               (if(<(distance(cross_product vec0 vec1)(list 0 0 0))1e-8)
                                   vec_offset
                                 (if(if(setq px0(inters p00 p01 p02 p03 nil))
                                        (setq px1(inters p00 p01 p02 p03 nil)))
                                     (mapcar '- px1 px0)
                                   vec_offset) )
                               ls_p0
                               (mapcar '(lambda(lst)
                                          (mapcar '(lambda(p)(mapcar '+ p veco))
                                                  lst))
                                       (list ls_p0 ls_p1))
                               )
                         
                         ))
                    (setq ls_p0(list ls_p0 ls_p1)))


                  
                  (if(apply 'and
                            (mapcar '(lambda(lst)
                                       (<(distance(cadr lst)(caddr lst))1e-8))
                                    ls_p0))
                      (setq ls_p0(list)))
                  
                  (mapcar
                   '(lambda(entna i)
                      (setq vnam(vlax-ename->vla-object entna)
                            ls_vnam_duct(cons(list(list "ARC"(1- num_temp)i)
                                                  (list "OBJ" entna vnam)
                                                  (cons "RADIUS" rr)
                                                  (cons "POSITION" ls_p0)
                                                  )
                                             ls_vnam_duct)
                            )

                      (arc2_dimstyle vnam)
                      (addkillobj vnam)
                      (if(= int_invisible_annotation 1)(vla-put-visible vnam :vlax-true))
                      (vla-put-color vnam int_colductdimedit)
                      )
                   (list entna0 entna1)(list 0 1))
                  
                  )) )
           )

         (cond

          
          ((= int_ductmode 0)
           (setq bool_replacegrread T int_grread 3 elem_grread(list 0 0 0)
                 bool_noeditdepth T
                 int_ductdepth 0 bool_ductedit T
                 bool_firsttime_editduct 0)
           
           ;;(setq bool_firsta
           
           (vla-put-visible vnam_currentinsert :vlax-false)
           (setq ls_vnam_visible(cons vnam_currentinsert ls_vnam_visible))
           )
          
          ((= int_ductmode 1)
           
           (setq bool_replacegrread T int_grread 3 elem_grread(list 0 0 0)
                 
                 bool_noeditdepth T bool_renewcopyduct T
                 vnam_road nil
                 int_ductdepth 0 bool_ductedit T)

           
           )
          )
         
         )
        
        ((= int_allow_noroad_temp 1)
         
         (x-alert(list 32076 36335 36984 25246 28961 12375 12391 20316 25104 12434 38283 22987 12375 12414 12377 )) ;;経路選択無しで作成を開始します
         
         (setq ls_p_road nil int_ductdepth 0 bool_ductedit T int_duct 0 int_selectmenu -1)
         
         )
        )
       
       ))
    
    (cons
     "KEYBOAD"
     (lambda( / ls_p bool_first);;(d- gr2_home()
       (cond
        ((if entna_depth
             (if(vl-position elem_grread(list 70 102 65318 65350 -218 -186))
                 ((lambda(lst / ii)
                    (while lst
                      (if(assoc "LINE"(car lst))(setq ii(1+ ii)))
                      (if(= ii 2)(setq lst nil)
                        (setq lst(cdr lst)))
                      )
                    (= ii 2))
                  ls_vnam_duct)))
         (setq str_edit "depthflatplane")
         
         )


        ((if(and(or(= elem_grread 13)(= int_grread 25))
                bool_ductedit ls_vnam_duct str_name_profile
                )
             ;;断面テンプレート(図面辞書の XRecord)から管ごとのパラメータを読む。
             ;;旧ブロック形式(terraduct3d$名前 + load_profile_block)は廃止。
             ;;1管あたりの並び :
             ;;  (名前 X Y 半径 管色 CORNER 全幅 全高 面取 保護コン色)
             ;;  ・テンプレートの幅/高さは中心からの半値なので2倍して全幅で渡す
             ;;    (下流で再び半分にして使うため)
             ;;  ・CORNER は 保護コンタイプ×面取り から導出
             ;;      全周 : 面取りあり 8 / なし 4
             ;;      下半 : 面取りあり -6 / なし -4
             ;;      なし : nil(保護コンを作らない)
             ;;  読めなかった(断面が空・削除済み)ときは nil になり、
             ;;  次の分岐(通常の単管作成)へ流れる
             (setq ls_profile
                   (mapcar
                    '(lambda(lst / name x y d ct w h f c1 c2)
                       (mapcar 'set '(name x y d ct w h f c1 c2)
                               (td3d_ds_fillpipe lst))
                       (list name x y(* 0.5 d)c1
                             (cond((= ct 2)nil)
                                  ((= ct 0)(if(> f 0.)8 4))
                                  (T(if(> f 0.)-6 -4)))
                             (* 2. w)(* 2. h)f c2))
                    (td3d_ds_read str_name_profile)))
             )
         (setq num_duct(1- int_min_duct))

         (setq ls_road(list))
         (while(<=(setq num_duct(1+ num_duct))int_max_duct)
           (setq num_x(- num_duct int_min_duct))
           (if(setq vnam(cadr(assoc "OBJ"(assoc(list "LINE" num_duct)ls_vnam_duct))))
                 
               ((lambda( / p1 p2 vec1 vec2 vecx)
                  (setq p1(vlax-curve-getstartpoint vnam)
                        p2(vlax-curve-getendpoint vnam)
                        vec1(unit_vector(mapcar '- p2 p1))
                        vec2(mapcar '-(unit_vector(carxyz vec1 0)))
                        vecx(trans-x(list 1. 0. 0.)vec2(list 0. 0. 1.))
                        
                        ls_hand
                        (mapcar
                         '(lambda(i / str lst vnam hand_road)
                            (setq lst(assoc "ROAD"(assoc(list "DEPTH" num_duct i)ls_vnam_duct)))
                            (setq str(caddr lst))
                            (if str str ""))
                         (list 0 1))
                        
                        ls_road(cons(list(list "LINE" num_duct) p1 p2 vec1 vec2 vecx ls_hand)ls_road)
                        )
                  
                  (if(setq lst(assoc(list "ARC" num_duct 0)ls_vnam_duct))
                      (setq vnam(caddr(assoc "OBJ" lst))
                            p1(vlax-safearray->list(vlax-variant-value(vla-get-ExtLine1EndPoint vnam)))
                            pc(vlax-safearray->list(vlax-variant-value(vla-get-AngleVertex vnam)))
                            
                            ls_road(cons(list(list "ARC" num_duct)p1(distance pc p1))ls_road)
                            )
                    )
                  ))
             
             )
           
           
           )

         (setq pitch_mesh(min pitch_project diam_duct_temp))
         (if(<(abs pitch_mesh)1e-8)
             (setq pitch_mesh diam_duct_temp))
         
         (setq ls_road(reverse ls_road) )
         (mapcar
          '(lambda(lst / ls_dummy str_pipename x_profile y_profile r_profile int_cc_profile
                       num_protect_profile w_profile h_profile f_profile int_cp_profile
                       )
             (mapcar 'set '(str_pipename x_profile y_profile r_profile int_cc_profile
                                         num_protect_profile w_profile h_profile f_profile
                                         int_cp_profile
                                         )
                     lst)
             (setq diam_duct_temp(* 2. r_profile))

             ;;ブロック名は管の名前。既にあるときは 名前$整数 の空き番号。
             ;;名前が無いときは従来どおり DUCT$ 連番
             (setq str_block_current
                   (if(and str_pipename(/= str_pipename ""))
                       (td3d_ds_uniquename str_pipename)
                     ((lambda( / bool i str str_ductname block)
                        (setq str "DUCT$" i 0 bool T)
                        (while bool
                          (setq i(1+ i)
                                str_ductname(strcat str(substr(itoa(+ 1000 i))2))
                                bool
                                (null
                                 (vl-catch-all-error-p
                                  (vl-catch-all-apply 'vla-Item(list vnam_blocktable str_ductname))))
                                )
                          )
                        str_ductname
                        ))
                     )
                   )
             
             (setq int_duct -1 int_depth 0 ls_pmesh(list)ls_pbar(list) p_arcend nil
                   ls_vnam_copy(list))
             (setq ls_dummy
                   (mapcar '(lambda(lst / p_line0 p_line1 vec_dire vec_plane vec_x ls_hand)
                              (if(=(caar lst)"LINE")
                                  (progn
                                    (mapcar 'set '(p_line0 p_line1 vec_dire vec_plane vec_x ls_hand)(cdr lst))
                                    
                                    (setq p_line0(mapcar '(lambda(a x y)(+ a(* x_profile x)(* y_profile y)))
                                                         p_line0 vec_x(list 0. 0. 1.))
                                          p_line1(mapcar '(lambda(a x y)(+ a(* x_profile x)(* y_profile y)))
                                                         p_line1 vec_x(list 0. 0. 1.))
                                          )
                                    (list(car lst)p_line0 p_line1 vec_dire vec_plane ls_hand)
                                    )
                                lst)
                              )
                           ls_road)
                   ls_crossline(vl-remove-if '(lambda(a)(=(caar a)"ARC"))ls_road)
                   ls_crossline(mapcar '(lambda(lst1 lst2)
                                          (inters(carxy(cadr lst1))(carxy(caddr lst1))
                                                 (carxy(cadr lst2))(carxy(caddr lst2))nil))
                                       ls_crossline(cdr ls_crossline))
                   )
             
             (setq ls_coordinate(list))
             (while ls_dummy
               (setq ls_line(car ls_dummy)ls_dummy(cdr ls_dummy)
                     ls_arc(car ls_dummy)ls_dummy(cdr ls_dummy)
                     )
               (mapcar 'set '(p_line0 p_line1 vec_dire vec_plane ls_hand)(cdr ls_line))
               
               (if ls_arc
                   (setq ls_line(cdar ls_dummy)
                         p_line10(car ls_line)p_line11(cadr ls_line)
                         px0(car ls_crossline)ls_crossline(cdr ls_crossline)
                         p_line1
                         (if(and(setq px1(inters(carxy p_line0)(carxy p_line1)(carxy p_line10)(carxy p_line11)nil))
                                px0)
                             (mapcar '(lambda(a b c)(+ a b(- c)))(cadr ls_arc)px1 px0)
                           (cadr ls_arc))
                         radius_arc(caddr ls_arc)
                         dd(apply '+(mapcar '*(mapcar '- p_line1 p_line0)vec_dire))
                         p_line1(mapcar '(lambda(a b)(+ a(* b dd)))p_line0 vec_dire)
                         )
                 
                 (setq radius_arc nil)
                 )
               
               (setq int_duct(1+ int_duct))
               
               (mapcar
                '(lambda(p1 ii h / p0)

                   (setq p0(car(project_to_ground(list p1)(list 0 0 1)
                                                 (list str_lasground height_ground)))
                         str_level(depth_level_str p0 p1)
                         entna(make_2pdimension
                               nil(list p0 p1 vec_plane
                                        (apply '+(mapcar '* vec_plane p0))
                                        nil(* 0.5 pi)
                                        0. str_level
                                        (if(vl-position str_dim_temp ls_dimstyle)
                                            str_dim_temp str_dimstyle_ductlevel)
                                        )
                               )
                         vnam(vlax-ename->vla-object entna)
                         ls_vnam_copy(cons vnam ls_vnam_copy)
                         )

                   (vla-put-Arrowhead1Type vnam 13)
                   (vla-put-Arrowhead2Type vnam 6)
                   (vla-put-ExtLine1Suppress vnam -1)
                   (vla-put-ExtLine2Suppress vnam -1)
                   (vla-put-HorizontalTextPosition vnam 3)
                   (if(= int_invisible_annotation 1)(vla-put-visible vnam :vlax-false))
                   (vla-put-color vnam int_colductdim)
                   (set_xda vnam(list(cons 1000 "DEPTH")
                                     (cons 1000 "NUM")(cons 1071 int_duct)
                                     (cons 1000 "SIDE")(cons 1071 ii)
                                     (cons 1000 "ROAD")(cons 1000 h)
                                     )
                            "terraduct3d")
                   )
                (list p_line0 p_line1)(list 0 1)ls_hand)
               
               (setq vnam
                     (vla-addline
                      (vla-get-modelspace(vla-get-activedocument(vlax-get-acad-object)))
                      (vlax-3d-point p_line0)(vlax-3d-point p_line1))
                     ls_vnam_copy(cons vnam ls_vnam_copy)
                     )
               
               (vla-put-color vnam int_colductdim)
               (set_xda vnam(list(cons 1000 "LINE")
                                 (cons 1000 "NUM")(cons 1071 int_duct))
                        "terraduct3d")

               (setq ls_coordinate(cons(list "LINE" p_line0 p_line1 vec_dire)ls_coordinate))
               

               
               (if ls_arc
                   (progn
                     (setq ls_arc(connect_twist_curve
                                  (list p_line0 p_line1 p_line10 p_line11 radius_arc
                                        length_arccenter nil "A"
                                        ;; ((lambda( / lst px0 px1 vec)
                                        ;;    (setq lst(cdr(assoc "POSITION" ls_currentarc0)))
                                        ;;    lst ))
                                        ))
                           )
                     
                     (setq delta_arcmove(* 0.1 radius_arc))
                     (if(= int_editarcradius 0)
                         (setq int_editarcposition_temp 3 )
                       (setq int_editarcposition_temp 1)
                       )

                     (if(=(car ls_arc)"BREAK")
                         (progn
                           
                           (if(cdr ls_arc)
                               (setq num_duct(1+ int_max_duct)
                                     bool_arcfirsttime
                                     (or(/= int_editarcposition 0)
                                        int_editarcposition_temp)
                                     ls_arcmove(cdr ls_arc)
                                     )
                             )
                           
                           (func_insertarc_initial)

                           ;;円弧位置の決定。
                           ;;  旧実装は p_line1 から一方向へ歩幅を増やしながら
                           ;;  bool_limit が立つまで探し続けていたが、
                           ;;   ・平行(linetype0)は bool_limit が立たず必ず無限ループ
                           ;;   ・交差(linetype1)は有効範囲が狭い(鋭角等)と
                           ;;     増える歩幅が範囲を跳び越えて発散
                           ;;   ・開始位置が有効範囲の逆側でも発散
                           ;;  だった。交差は位置を有効範囲へ直接クランプして
                           ;;  1回で確定し、ねじれだけ反復(上限つき)にする
                           (setq bool_limit nil ls_arc_temp nil
                                 p_first p_line1 num 1 num_max 200)
                           (cond
                            ((= bool_linetype 1)
                             ;;有効範囲(dist_limit01〜00)へ射影位置をクランプ。
                             ;;範囲の順序が逆転していても min/max で吸収する
                             ((lambda( / dmin dmax d)
                                (setq dmin(min dist_limit00 dist_limit01)
                                      dmax(max dist_limit00 dist_limit01)
                                      d(apply '+(mapcar '* p_line1 vec_line0))
                                      d(max(+ dmin(* 0.01(- dmax dmin)))
                                            (min d(- dmax(* 0.01(- dmax dmin)))))
                                      )
                                (func_insertarc_move
                                 (mapcar '(lambda(a b)
                                            (+ a(*(- d(apply '+(mapcar '* p_line01 vec_line0)))
                                                  b)))
                                         p_line01 vec_line0)
                                 'ls_arc_temp 0)
                                ))
                             )
                            ((= bool_linetype 2)
                             ;;ねじれ : 従来どおり歩進探索。ただし上限を設け、
                             ;;見つからなければ起点側の限界位置で確定する
                             (func_insertarc_move p_line1 'ls_arc_temp 0)
                             (while(and(null bool_limit)(<(setq num(1+ num))num_max))
                               (setq p_line1(mapcar '(lambda(a b)(+ a(* num -1 delta_arcmove b)))
                                                    p_line1 vec_dire))
                               (func_insertarc_move p_line1 'ls_arc_temp 0)
                               )
                             (if(and(null bool_limit)p_limit0)
                                 (func_insertarc_move p_limit0 'ls_arc_temp 0))
                             )
                            (T;;平行 : どの位置でも作れるので1回で確定
                             (func_insertarc_move p_line1 'ls_arc_temp 0)
                             )
                            )
                           (if(null ls_arc_temp)
                               ;;円弧を設定できませんでした
                               (princ(mix_strasc(list "\n" 20870 24359 12434 35373 23450 12391 12365 12414 12379 12435 12391 12375 12383))))

                           )
                       (progn(alert "profileerror")(quit))
                       )
                     
                     (setq rr radius_arc)
                     (mapcar
                      '(lambda(lst ii / e vnam vec_normal pc p0 p1 p2 length_straight e_out)
                         (mapcar 'set '(pc p0 p1 p2 vec_normal length_straight)lst)
                         
                         (setq dist_normal(apply '+(mapcar '* pc vec_normal))
                               e_out
                               (make_arcdimension
                                nil(list pc p0 p1 p2 rr vec_normal dist_normal
                                         (arc2_dimtext rr p1 p2)
                                         str_dimstyle_ductlevel))
                               )
                         
                         (setq vnam(vlax-ename->vla-object e_out)
                               ls_vnam_copy(cons vnam ls_vnam_copy))
                         
                         (setq ls_p_dimtext (cons(cons vnam p2) ls_p_dimtext))
                         
                         (arc2_dimstyle vnam)
                         
                         (set_xda vnam(list(cons 1000 "ARC")
                                           (cons 1000 "NUM")(cons 1071 int_duct)
                                           (cons 1000 "SIDE")(cons 1071 ii)
                                           (cons 1000 "RADIUS")(cons 1040 radius_arc)
                                           )
                                  "terraduct3d")
                         
                         (if(= int_invisible_annotation 1)(vla-put-visible vnam :vlax-true))
                         (vla-put-color vnam int_colductdim)

                         (setq ls_coordinate(cons(list "ARC" pc p0 p1 vec_normal)ls_coordinate))
                         
                         
                         e_out
                         )
                      ls_arc_temp(list 0 1))
                     
                     
                     )
                 )
               
               
               )


             (setq ls_coordinate(reverse ls_coordinate)
                   p_start(cadr(car ls_coordinate))
                   p_last(caddr(last ls_coordinate))
                   vec1(cadddr(car ls_coordinate))
                   ls_pmesh(list(list p_start vec1))
                   ls_pbar(list(list p_start nil vec1))
                   ls_coordinate(cdr ls_coordinate)
                   )
             (if ls_coordinate T(setq ls_coordinate(list(list "LINE"))))
             ;;anchor
             (while ls_coordinate
               (setq lst(car ls_coordinate)ls_coordinate(cdr ls_coordinate)
                     str_type(car lst))
               
               (if(if(= str_type "ARC")(setq p_end(caddr lst))
                    (if(null ls_coordinate)(setq p_end p_last)
                      (setq p_end nil)))
                   (if(<(distance p_start p_end)1e-8)T
                     ((lambda( / d n i dd pm)
                        (if(null ls_coordinate)
                            (setq ls_pbar(cons(list p_end nil vec1)ls_pbar)))
                        (setq d(distance p_start p_end) n(1+(fix(/ d pitch_mesh))) d(/ d n)
                              dd 0)
                        (while(>(setq n(1- n))-1)
                          (setq dd(+ dd d)
                                pm(mapcar '(lambda(a b)(+ a(* dd b)))p_start vec1)
                                ls_pmesh(cons(list pm vec1)ls_pmesh)
                                )
                          )
                        ))))
               
               (if(if(= str_type "ARC")
                      (progn
                        (mapcar 'set '(p15 p13 p14 vec_normal)(cdr lst))
                        (setq p_start p14)
                        (>(distance p13 p14)1e-8)
                        ))
                   (progn
                     (setq vec13(mapcar '- p13 p15)
                           vec14(mapcar '- p14 p15)
                           rr(distance p13 p15)
                           vec13(mapcar '(lambda(a)(/ a rr))vec13)
                           vec14(mapcar '(lambda(a)(/ a rr))vec14)
                           vec0(cross_product vec_normal vec13)
                           vec1(cross_product vec_normal vec14)
                           )
                     
                     (if(<(apply '+(mapcar '* vec0 vec14))0)(setq vec0(mapcar '- vec0)))
                     (if(>(apply '+(mapcar '* vec1 vec13))0)(setq vec1(mapcar '- vec1)))

                     (if(<(distance(caar ls_pbar)p13)1e-8)(setq ls_pbar(cdr ls_pbar)))
                     (setq ls_pbar(cons(list p13 p15 vec0)ls_pbar)
                           ls_pbar(cons(list p14 nil vec1)ls_pbar)
                           )
                     ((lambda( / d n i ang r vec_x vec_y pm dd c s v)
                        (setq ang(atan(distance(cross_product vec13 vec14)(list 0 0 0))
                                      (apply '+(mapcar '* vec13 vec14)))
                              vec_x(mapcar '(lambda(a)(* a rr))vec13)
                              vec_y(mapcar '(lambda(a)(* a rr))vec0)
                              d(* rr ang) n(1+(fix(/ d(min(* 0.5 rr) pitch_mesh))))
                              d(/ ang n)
                              ang 0)
                        
                        (while(>(setq n(1- n))-1)
                          (setq ang(+ ang d)c(cos ang)s(sin ang)
                                v(mapcar '(lambda(x y)(+ (* -1 s x)(* c y)))vec13 vec0)
                                pm(mapcar '(lambda(a x y)(+ a(* c x)(* s y)))p15 vec_x vec_y)
                                ls_pmesh(cons(list pm v)ls_pmesh)
                                )
                          )
                        ))
                     
                     ))
               )

             
             (progn;;作成
               (setq ls_pcenterline(mapcar 'car(reverse ls_pmesh)))
               
               (if(= int_ductsolidmesh 1)
                   (progn
                     (setq ls_pbar(reverse ls_pbar)
                           entna(bendpipe_lwpsld
                                 (* 0.5 diam_duct_temp) ls_pbar (getvar "CLAYER") nil)
                           entna(bendpipe_lwpsld (* 0.5 diam_duct_temp) ls_pbar (getvar "CLAYER") nil)
                           vnam(vlax-ename->vla-object entna)
                           )

                     
                     )
                 (progn
                   (setq numy 32
                         ls_intmesh(inclist 0 numy)
                         ang_d(/(* 2. pi)numy)
                         r(* 0.5 diam_duct_temp)
                         vecxp nil vecyp nil
                         )
                   
                   (setq ls_pduct
                         (mapcar
                          '(lambda(lst / p v vecx vecy)
                             (setq p(car lst)v(cadr lst)
                                   v(unit_vector v )
                                   vecx(trans-x(list 1 0 0)v(list 0 0 1))
                                   vecy(trans-x(list 0 1 0)v(list 0 0 1))
                                   )

                             (if(if vecxp(>(apply '+(mapcar '* vecx vecxp))0)T)T
                               (setq vecx vecxp))
                             (setq vecxp vecx)
                             (if(<(caddr vecy)0)(setq vecy(mapcar '- vecy)))
                             (mapcar '(lambda(i / c s)
                                        (setq c(cos(* ang_d i))s(sin(* ang_d i)))
                                        (mapcar '(lambda(a x y)(+(* r c x)(* r s y)a))
                                                p vecx vecy))
                                     ls_intmesh)
                             )
                          (reverse ls_pmesh)
                          )
                         
                         numx(length ls_pduct)
                         ls_p(apply 'append(apply 'append ls_pduct))
                         )
                   
                   (setq array_mesh(vlax-make-safearray vlax-vbDouble(cons 0(1-(length ls_p)))))
                   (vlax-safearray-fill array_mesh ls_p)
                   (setq vnam
                         (vla-Add3DMesh
                          (vla-get-ModelSpace(vla-get-ActiveDocument (vlax-get-acad-object)))
                          numx numy array_mesh)
                         
                         )
                   (vla-put-nclose vnam :vlax-true)
                   )
                 )

               (vla-put-color vnam int_cc_profile)
               (setq ls_vnam_copy(cons vnam ls_vnam_copy))
               (vla-put-visible vnam :vlax-true)
               
               (set_xda vnam(list(cons 1000 "DUCTSOLID")
                                 (cons 1000 "DIAM")(cons 1040 diam_duct_temp)
                                 )
                        "terraduct3d")
               
               (setq ls_p(apply 'append ls_pcenterline)
                     array_p(vlax-make-safearray vlax-vbDouble(cons 0(1-(length ls_p)))))
               (vlax-safearray-fill array_p ls_p)
               (setq vnam(vla-Add3dPoly
                          (vla-get-ModelSpace(vla-get-ActiveDocument(vlax-get-acad-object)))
                          array_p))
               (setq ls_vnam_copy(cons vnam ls_vnam_copy))
               (set_xda vnam(list(cons 1000 "CENTERLINE"))"terraduct3d")
               
               (if(setq numy num_protect_profile)
                   (progn
                     (setq int_corner numy
                           
                           w(* 0.5 w_profile)
                           h(* 0.5 h_profile)
                           f f_profile
                           
                           ls_pmesh
                           (mapcar
                            '(lambda(lst / p v vecx vecy)
                               (setq p(car lst)v(cadr lst)
                                     v(unit_vector(carxyz v 0.))
                                     vecx(trans-x(list 1 0 0)v(list 0 0 1))
                                     vecy(trans-x(list 0 1 0)v(list 0 0 1))
                                     )
                               
                               (vl-remove
                                nil
                                (mapcar '(lambda(lst / bool iw iwf ih ihf)
                                           (mapcar 'set '(bool iw iwf ih ihf)lst)
                                           (if(vl-position numy bool)
                                               (mapcar '(lambda(a x y)(+(*(+(* iw w)(* iwf f))x)
                                                                        (*(+(* ih h)(* ihf f))y) a))
                                                       p vecx vecy))
                                           )
                                        (list(list(list 8 4)-1  1 1 0)
                                             (list(list 8)  -1  0 1 -1)
                                             (list(list -6 -4)-1 0 0 0)
                                             (list(list 8 4 -6 -4)-1 0 -1 1)
                                             (list(list 8 -6)-1  1 -1 0)
                                             (list(list 8 -6) 1 -1 -1 0)
                                             (list(list 8 4 -6 -4) 1 0 -1 1)
                                             (list(list -6 -4) 1 0 0 0)
                                             (list(list 8)   1  0 1 -1)
                                             (list(list 8 4) 1 -1 1 0)
                                             ))
                                )
                               )
                            (reverse ls_pmesh)
                            )
                           
                           numx(length ls_pmesh)
                           numy(abs numy)
                           ls_p(apply 'append(apply 'append ls_pmesh))
                           )
                     
                     (setq array_mesh(vlax-make-safearray vlax-vbDouble(cons 0(1-(length ls_p)))))
                     (vlax-safearray-fill array_mesh ls_p)
                     (setq vnam
                           (vla-Add3DMesh
                            (vla-get-ModelSpace(vla-get-ActiveDocument (vlax-get-acad-object)))
                            numx numy array_mesh)

                           )
                     
                     (vla-put-layer vnam str_layprotect)
                     ;;保護コンの色はテンプレートの指定を使う(無ければ従来色)
                     (vla-put-color vnam(if int_cp_profile int_cp_profile int_colprotect))
                     (vla-put-nclose vnam :vlax-true)

                     (setq ls_vnam_copy(cons vnam ls_vnam_copy))
                     ;;XDATA もこの管自身の寸法を記録する(以前は入力欄の値を
                     ;;そのまま書いていたため断面テンプレートと食い違っていた)
                     (set_xda vnam(list(cons 1000 "CONMESH")
                                       (cons 1000 "CORNER")(cons 1071 int_corner)
                                       (cons 1000 "WIDTH")(cons 1040 w_profile)
                                       (cons 1000 "HEIGHT")(cons 1040 h_profile)
                                       (cons 1000 "FILET")(cons 1040 f_profile)
                                       )
                              "terraduct3d")
                     ))




               (setq ls_p(apply 'append ls_pcenterline)
                     array_p(vlax-make-safearray vlax-vbDouble(cons 0(1-(length ls_p)))))
               (vlax-safearray-fill array_p ls_p)
               (setq vnam(vla-Add3dPoly
                          (vla-get-ModelSpace(vla-get-ActiveDocument(vlax-get-acad-object)))
                          array_p))
               (setq ls_vnam_copy(cons vnam ls_vnam_copy))
               (set_xda vnam(list(cons 1000 "CENTERLINE"))"terraduct3d")
               
               )

             (if(null ls_vnam_copy)
                 (x-alert(list 28145 24230 35373 23450 12364 36275 12426 12394 12356 12383 12417 20309 12418 20316 25104 12373 12428 12414 12379 12435 )) ;;深度設定が足りないため何も作成されません
               (progn
                 
                 (if(vl-catch-all-error-p
                     (setq block(vl-catch-all-apply 'vla-Item(list vnam_blocktable str_block_current))))
                     (setq block(vla-Add vnam_blockTable(vlax-3d-point 0 0 0)str_block_current) )
                   )

                 (setq ls_vla-release(cons block ls_vla-release) )

                 (vlax-for obj block(vla-delete obj))
                 (vla-copyobjects
                  (vla-get-ActiveDocument (vlax-get-acad-object))
                  (vlax-make-variant
                   (vlax-safearray-fill
                    (vlax-make-safearray vlax-vbObject(cons 0 (1-(length ls_vnam_copy))))
                    (reverse ls_vnam_copy))
                   )
                  block)
                 
                 (mapcar '(lambda(v)
                            (vlax-release-object v)
                            (setq ls_vla-release(vl-remove v ls_vla-release))
                            )
                         (list block))
                 
                 (mapcar '(lambda(v)
                            (vla-delete v)
                            (exckillobj v)
                            )
                         ls_vnam_copy)

                 (setq vnam(vla-InsertBlock
                            (vla-get-ModelSpace(vla-get-ActiveDocument(vlax-get-acad-object)))
                            (vlax-3d-point 0 0 0)str_block_current 1 1 1 0)
                       )
                 (set_xda vnam(list(cons 1000 "DUCTBLOCK"))"terraduct3d")
                 ))
             
             
             (mapcar '(lambda(lst)
                        (if(setq lst(cdr(assoc "OBJ" lst)))
                            (mapcar '(lambda(a)(if(=(type a)'VLA-OBJECT)
                                                   (if(vlax-erased-p a)T(vla-delete a))))
                                    lst)
                          ))
                     ls_vnam_duct)
             
             (setq ls_vnam_duct(list) vnam_depth nil entna_depth nil
                   bool_ductedit(if vnam_road T)
                   int_ductdepth 0 int_selectmenu nil str_ductname nil
                   int_max_duct 0 int_min_duct 0 )

             (if(= int_editstatus 2)
                 (progn
                   (setq bool_ductedit(if vnam_road T)
                         int_editstatus nil)
                   ))
             
             
             
             )
          ls_profile
          )

         (setq ls_vnam_duct nil)
         (if vnam_currentinsert
             (progn
               (vla-put-visible vnam_currentinsert :vlax-true)
               (setq ls_vnam_visible(vl-remove vnam_currentinsert ls_vnam_visible)
                     vnam_currentinsert nil )
               ))
         
         (if(= int_editstatus 2)
             (progn
               (setq bool_ductedit(if vnam_road T)
                     int_editstatus nil)
               ))
         
         )
        
        ((and(or(= elem_grread 13)(= int_grread 25))
             bool_ductedit ls_vnam_duct)
         (setq num_duct(1- int_min_duct)ls_vnam_copy(list))
        
         (while(<=(setq num_duct(1+ num_duct))int_max_duct)
           (setq num_x(- num_duct int_min_duct))
           (if(setq vnam(cadr(assoc "OBJ"(assoc(list "LINE" num_duct)ls_vnam_duct))))
               (progn
                 (setq vec_line
                       ((lambda( / p1 p2 vec)
                          (setq p1(vlax-curve-getstartpoint vnam)
                                p2(vlax-curve-getendpoint vnam)
                                vec(unit_vector(mapcar '- p1 p2))
                                )
                          (if(and(<(abs(car vec))1e-8)(<(abs(cadr vec))1e-8))T
                            (setq vec(unit_vector(carxyz vec 0))))
                          vec))
                       ls_vnam_copy(cons vnam ls_vnam_copy)
                       )
                 (vla-put-color vnam int_colductdim)
                 (set_xda vnam(list(cons 1000 "LINE")
                                   (cons 1000 "NUM")(cons 1071 num_x))
                          "terraduct3d")
                 
                 (mapcar
                  '(lambda(ii / entna ls_gcode p13 p14 dd str_level)
                     (setq lst(assoc(list "DEPTH" num_duct ii)ls_vnam_duct)
                           entna(cadr(assoc "OBJ" lst))
                           ls_gcode(entget entna)
                           p13(cdr(assoc 13 ls_gcode))p14(cdr(assoc 14 ls_gcode))
                           str_level(cdr(assoc 1 ls_gcode))
                           dd(apply '+(mapcar '* vec_line p13))
                           )

                     
                     (make_2pdimension
                      entna(list p13 p14 vec_line dd nil(* 0.5 pi)
                                 0. str_level str_dimstyle_ductlevel))
                     (setq vnam(caddr(assoc "OBJ" lst))
                           ls_vnam_copy(cons vnam ls_vnam_copy)
                           )

                     (setq ls_p_dimtext (cons(cons vnam p14) ls_p_dimtext))

                     (if(= int_invisible_annotation 1)(vla-put-visible vnam :vlax-false))
                     (vla-put-color vnam int_colductdim)
                     (set_xda vnam(list(cons 1000 "DEPTH")
                                       (cons 1000 "NUM")(cons 1071 num_x)
                                       (cons 1000 "SIDE")(cons 1071 ii)
                                       (cons 1000 "ROAD")(cons 1000(caddr(assoc "ROAD" lst)))
                                       )
                              "terraduct3d")
                     )
                  (list 0 1))
                 
                 ))
           
           (mapcar
            '(lambda(ii / )
               (if(setq lst(assoc(list "ARC" num_duct ii)ls_vnam_duct))
                   (progn
                     (setq vnam(caddr(assoc "OBJ" lst))
                           ls_vnam_copy(cons vnam ls_vnam_copy))
                     (if(= int_invisible_annotation 1)(vla-put-visible vnam :vlax-false))
                     (vla-put-color vnam int_colductdim)
                     (set_xda vnam(list(cons 1000 "ARC")
                                       (cons 1000 "NUM")(cons 1071 num_x)
                                       (cons 1000 "SIDE")(cons 1071 ii)
                                       (cons 1000 "RADIUS")(cons 1040(cdr(assoc "RADIUS" lst)))
                                       )
                              "terraduct3d")
                     ))
               )
            (list 0 1))
           
           )

         
         (if(setq lst(assoc(list "SOLID" 0)ls_vnam_duct))
             (progn
               (setq vnam(cadr(assoc "OBJ" lst))
                     ls_vnam_copy(cons vnam ls_vnam_copy))
               (vla-put-visible vnam :vlax-true)
               (set_xda vnam(list(cons 1000 "DUCTSOLID")
                                 (cons 1000 "DIAM")(cons 1040(cdr(assoc "DIAM" lst)))
                                 )
                        "terraduct3d")

               (if ls_pcenterline
                   (progn
                     (setq ls_p(apply 'append ls_pcenterline)
                           array_p(vlax-make-safearray vlax-vbDouble(cons 0(1-(length ls_p)))))
                     (vlax-safearray-fill array_p ls_p)
                     (setq vnam(vla-Add3dPoly
                                (vla-get-ModelSpace(vla-get-ActiveDocument(vlax-get-acad-object)))
                                array_p))
                     (addkillobj vnam)
                     (setq ls_vnam_copy(cons vnam ls_vnam_copy))
                     (set_xda vnam(list(cons 1000 "CENTERLINE"))"terraduct3d")
                     ))
               ))

         (if(setq lst(assoc(list "MESH" 0)ls_vnam_duct))
             (progn
               (setq vnam(cadr(assoc "OBJ" lst))
                     ls_vnam_copy(cons vnam ls_vnam_copy))
               (vla-put-visible vnam :vlax-true)
               (set_xda vnam(list(cons 1000 "CONMESH")
                                 (cons 1000 "CORNER")(cons 1071(cdr(assoc "CORNER" lst)))
                                 (cons 1000 "WIDTH")(cons 1040(cdr(assoc "WIDTH" lst)))
                                 (cons 1000 "HEIGHT")(cons 1040(cdr(assoc "HEIGHT" lst)))
                                 (cons 1000 "FILET")(cons 1040(cdr(assoc "FILET" lst)))
                                 )
                        "terraduct3d")
               ))
         
         (if(null ls_vnam_copy)
             (x-alert(list 28145 24230 35373 23450 12364 36275 12426 12394 12356 12383 12417 20309 12418 20316 25104 12373 12428 12414 12379 12435 )) ;;深度設定が足りないため何も作成されません
           (progn
             
             (if(vl-catch-all-error-p
                 (setq block(vl-catch-all-apply 'vla-Item(list vnam_blocktable str_ductname))))
                 (setq block(vla-Add vnam_blockTable(vlax-3d-point 0 0 0)str_ductname) )
               (progn
                 (if vnam_currentinsert
                     (progn
                       (vla-delete vnam_currentinsert)
                       (setq ls_vnam_visible
                             (vl-remove vnam_currentinsert ls_vnam_visible)
                             vnam_currentinsert nil)
                       ))
                 (if(setq set_ent(ssget "X"(list(cons 2 str_ductname))))
                     (progn
                       (setq num(sslength set_ent))
                       (while(>(setq num(1- num))-1)
                         (setq vnam(vlax-ename->vla-object(ssname set_ent num)))
                         (vla-delete vnam)
                         )
                       ))
                 
                 (vla-delete block)
                 (mapcar '(lambda(v)
                            (vlax-release-object v)
                            (setq ls_vla-release(vl-remove v ls_vla-release))
                            )
                         (list block))
                 (setq block(vla-Add vnam_blockTable(vlax-3d-point 0 0 0)str_ductname))
                 )
               )
             
             (setq ls_vla-release(cons block ls_vla-release) )
             (vlax-for obj block(vla-delete obj))
             (vla-copyobjects
              (vla-get-ActiveDocument (vlax-get-acad-object))
              (vlax-make-variant
               (vlax-safearray-fill
                (vlax-make-safearray vlax-vbObject(cons 0 (1-(length ls_vnam_copy))))
                (reverse ls_vnam_copy))
               )
              block)
             
             (mapcar '(lambda(v)
                        (vlax-release-object v)
                        (setq ls_vla-release(vl-remove v ls_vla-release))
                        )
                     (list block))
             
             (mapcar '(lambda(v)
                        (vla-delete v)
                        (exckillobj v)
                        )
                     ls_vnam_copy)

             (setq vnam(vla-InsertBlock
                        (vla-get-ModelSpace(vla-get-ActiveDocument(vlax-get-acad-object)))
                        (vlax-3d-point 0 0 0)str_ductname 1 1 1 0)
                   )
             (set_xda vnam(list(cons 1000 "DUCTBLOCK"))"terraduct3d")
             ))

         (mapcar '(lambda(lst)
                    (if(setq lst(cdr(assoc "OBJ" lst)))
                        (mapcar '(lambda(a)(if(=(type a)'VLA-OBJECT)
                                               (if(vlax-erased-p a)T(vla-delete a))))
                                lst)
                      ))
                 ls_vnam_duct)
         
         (setq ls_vnam_duct(list) vnam_depth nil entna_depth nil
               bool_ductedit(if vnam_road T)
               int_ductdepth 0 int_selectmenu nil str_ductname nil
               int_max_duct 0 int_min_duct 0 )

         (if(= int_editstatus 2)
             (progn
               (setq bool_ductedit(if vnam_road T)
                     int_editstatus nil)
               ))
         
         )
        
        ((and(or(= elem_grread 13)(= int_grread 25))
             bool_ductedit)
         (setq bool_ductedit(if vnam_road T)
               str_edit "home")
         
         )


        
        ((and(or(= elem_grread 13)(= int_grread 25))
             (= int_ductmode 2))
         
         (mapcar
          '(lambda(vnam / str set_ent num)
             
             (vla-getXData vnam "terraduct3d" 'array_Type 'array_Data )
             (if(if array_data
                    (progn
                      (setq ls_xdata
                            (split_list 0(mapcar 'vlax-variant-value
                                                 (vlax-safearray->list array_data))))
                      (=(cdr(assoc "terraduct3d" ls_xdata))"DUCTBLOCK")
                      ))
                 (progn
                   (setq str(vla-get-name vnam)
                         vnam_insertname
                         (vla-Item(vla-get-Blocks (vla-get-ActiveDocument(vlax-get-acad-object)))str))
                   ;;(vla-delete vnam)
                   (if(setq set_ent(ssget "X"(list(cons 2 str))))
                       (progn
                         (setq num(sslength set_ent))
                         (while(>(setq num(1- num))-1)
                           (setq vnam(vlax-ename->vla-object(ssname set_ent num)))
                           (vla-delete vnam)
                           )
                         ))

                   (if (vl-catch-all-error-p
                        (vl-catch-all-apply 'vla-get-Handle (list vnam_insertname)))
                       T(vla-delete vnam_insertname))
                   
                   ;; (vl-remove vnam_insertname ls_vnam_highlight)
                   )
               )
             
             
             )
          ls_vnam_select)
         (setq ls_vnam_highlight(list)
               ls_vnam_select(list))
         )
        )
       
       
       ))
    )
   
   
   (list
    "insertarc" ;;edsym
    (cons
     "INITIAL"
     (lambda(bool / delta_arc bool_loop);;initial
       (if(car bool)
           (progn
             ;;temp
             (setq bool_point nil
                   bool_selectent nil bool_select nil int_selectmode -1
                   ;;クリックはすべて「円弧位置の指定」であって図形選択ではない。
                   ;;ls_ssget が nil だと汎用クリック処理の無フィルタ ssget が
                   ;;角の座標にある管路の LINE を拾って ls_vnam_select を汚し、
                   ;;makeductmain へ戻ったあと経路(vnam_road)に化けるため、
                   ;;何にも一致しないフィルタで図形選択を止める
                   ls_ssget(list(cons 0 "TD3D_NEVER_MATCH"))
                   xtype_ssget nil xdata_ssget nil
                   )

             ;;bool_tempdistlength

             (func_insertarc_initial)
             
             (setq ls_entna_arctemp
                   (mapcar '(lambda(i / v e)
                              (setq e(make_arcdimension
                                      nil(list(list 0 0 0)(list 1 0 0)(list 1 0 0)(list 1 0 0)1(list 0 0 1)
                                              0 " " str_dimstyle_ductlevel))
                                    vnam(vlax-ename->vla-object e)
                                    )
                              

                              (vla-put-Arrowhead1Type vnam 19)
                              (vla-put-Arrowhead2Type vnam 19)
                              (vla-put-ExtLine1Suppress vnam -1)
                              (vla-put-ExtLine2Suppress vnam -1)
                              (addkillobj vnam)
                              (list e vnam))
                           (list 0 1))
                   p_arcstart nil
                   int_baseline 0

                   func_guidemenu
                   (lambda()
                     ;;todo
                     
                     (mix_strasc
                      (list
                       ;;クリックして起点終点の通過位置を決定
                       ;;または通過点採用のキー入力をしてください
                       ;;Enter:変更せずに戻る
                       12463 12522 12483 12463 12375 12390 36215 28857 32066 28857 12398 36890 36942 20301 32622 12434 27770 23450 "\n" 12414 12383 12399 36890 36942 28857 25505 29992 12398 12461 12540 20837 21147 12434 12375 12390 12367 12384 12373 12356
                       "\nEnter:"
                       (if p_arcprev
                           (list 22793 26356 12379 12378 12395 25147 12427 )
                         (list 21021 22238 12394 12398 12391 24517 12378 12393 12371 12363 36984 25246 12375 12390 12367 12384 12373 12356 ))
                       
                       )
                      ) )
                   
                   
                   ls_guideexplane
                   (mapcar
                    'mix_strasc
                    (list(list " - " 20870 24359 12398 36215 28857 12418 12375 12367 12399 32066 28857 12364 36890 36942 12377 12427 20301 32622 12434 27770 23450 12377 12427 )
                         ;;円弧の起点もしくは終点が通過する位置を決定する
                         ))
                   
                   ls_guidemenu
                   (list
                    (list(list 82) ;;R経路の曲げ半径
                         (cons "ITEM"(list 32076 36335 12398 26354 12370 21322 24452))
                         (cons "INPUT"(lambda() 'radius_arcmove))
                         (cons "HELP"(lambda()(mix_strasc(list 31649 36335 12364 26354 32218 12392 12394 12427 31623 25152 12395 12362 12369 12427 26354 12370 21322 24452(if int_selectmenu str_guide_inputval str_guide_selectval)))))
                         
                         )
                    
                    (list(list 49);;近接点切替
                         (cons "ITEM"(list 36817 25509 28857 20999 26367  ))
                         (cons "INPUTSWITCH"
                               (lambda()
                                 (list 'int_baseline
                                       (mapcar 'mix_strasc
                                               (list(list "{\\C" str_gcol_g ";" 36215 28857 20596 "}")
                                                    (list "{\\C" str_gcol_c ";"32066 28857 20596 "}"))))
                                 ))
                         ;;マウスカーソルに近接する円弧が起点側か終点側か選択してください
                         (cons "HELP"(lambda()(mix_strasc(list 12510 12454 12473 12459 12540 12477 12523 12395 36817 25509 12377 12427 20870 24359 12364 36215 28857 20596 12363 32066 28857 20596 12363 36984 25246 12375 12390 12367 12384 12373 12356))))
                         
                         )

                    (list(list 50);;起点側終点を通過する円弧を採用する
                         (cons "ITEM"(list 36215 28857 20596 32066 28857 12434 36890 36942 12377 12427 20870 24359 12434 25505 29992 12377 12427))
                         (cons "LOADFUNCTION"
                               (lambda( / p)
                                 ;;ねじれ(linetype2)のときは限界探索で求めた線0上の点を使う
                                 (setq p(if(= bool_linetype 2)p_limit0 p_line01))
                                 (if p
                                     (setq int_baseline 0 elem_grread p
                                           bool_replacegrread T int_grread 3)
                                   ;;限界位置が計算できていません
                                   (x-alert(list 38480 30028 20301 32622 12364 35336 31639 12391 12365 12390 12356 12414 12379 12435)))
                                 ))
                         (cons "HELP"(lambda()(mix_strasc(list 36215 28857 20596 32066 28857 12434 36890 36942 12377 12427 20870 24359 12434 25505 29992 12377 12427))))
                         )
                    
                    (list(list 51);;終点側起点を通過する円弧を採用する
                         (cons "ITEM"(list 32066 28857 20596 36215 28857 12434 36890 36942 12377 12427 20870 24359 12434 25505 29992 12377 12427))
                         (cons "LOADFUNCTION"
                               (lambda( / p)
                                 ;;ねじれ(linetype2)のとき p_limit1 は線1上の点なので
                                 ;;基準も終点側(int_baseline=1)にする。
                                 ;;※以前は int_baseline 0 のまま p_limit1 を渡していたため、
                                 ;;  線0基準・ビュー方向依存の投影で毎回違う位置に化けていた
                                 (setq p(if(= bool_linetype 2)p_limit1 p_line10))
                                 (if p
                                     (setq int_baseline 1 elem_grread p
                                           bool_replacegrread T int_grread 3)
                                   ;;限界位置が計算できていません
                                   (x-alert(list 38480 30028 20301 32622 12364 35336 31639 12391 12365 12390 12356 12414 12379 12435)))
                                 ))
                         (cons "HELP"(lambda()(mix_strasc(list 32066 28857 20596 36215 28857 12434 36890 36942 12377 12427 20870 24359 12434 25505 29992 12377 12427))))
                         )
                    
                    (list(list "ENTER");;変更せずに戻る
                         (cons "ITEM"(list 22793 26356 12379 12378 12395 25147 12427 ))
                         (cons "LOADFUNCTION"
                               (lambda()
                                 (if p_arcprev
                                     (setq bool_replacegrread T int_grread 3
                                           int_baseline 0 elem_grread p_arcprev )
                                   (x-alert(list 21021 22238 12394 12398 12391 24517 12378 12393 12371 12363 36984 25246 12375 12390 12367 12384 12373 12356 ))
                                   ;;初回なので必ずどこか選択してください
                                   )
                                 )))
                    )
                   
                   )
             

             (if bool_arcfirsttime
                 (setq bool_arcfirsttime nil bool_replacegrread T
                       int_grread 2
                       elem_grread(+ 49(if int_editarcposition_temp
                                           int_editarcposition_temp int_editarcposition))
                       ))
             
             ))
       
       (if(cadr bool) (list ) )
       ))
    
    (cons
     "MOVE"
     (lambda( / ls_grdraw bool_limit);;gr5
       (if(if vec_normal(<(abs(apply '+(mapcar '* vec_normal vec_view)))1e-8))
           (progn;;円弧の法線とビュー方向が直交しているとき描画できません;;ビューを回転させてください
             (x-alert(list 20870 24359 12398 27861 32218 12392 12499 12517 12540 26041 21521 12364
                           30452 20132 12375 12390 12356 12427 12392 12365
                           25551 30011 12391 12365 12414 12379 12435
                           "\n" 12499 12517 12540 12434 22238 36578
                           12373 12379 12390 12367 12384 12373 12356))
             (setq bool_replacegrread T int_grread 11)
             )
         (progn

           
           (setq p_proj
                 ((lambda(p vec_normal dist_normal ps / d  vec)
                    (setq d(- dist_normal(apply '+(mapcar '* p vec_normal))))
                    (if ps(setq vec vec_normal)
                      (setq d(/ d(apply '+(mapcar '* vec_view vec_normal)))vec vec_view))
                    (mapcar '(lambda(a b)(+ a(* d b)))p vec)
                    )
                  elem_grread
                  ;;ねじれのとき終点側(int_baseline=1)は線1を含む平面へ投影する。
                  ;;線0側の平面のままだと、平面上に無い点の投影がビュー方向依存になる
                  (if(and(= bool_linetype 2)(= int_baseline 1)vec_normal1)
                      vec_normal1 vec_normal)
                  (if(and(= bool_linetype 2)(= int_baseline 1)vec_normal1)
                      dist_normal1 dist_normal)
                  nil
                  )
                 
                 d(apply '+(mapcar '*(mapcar '- p_proj(if(= int_baseline 0)p_line01 p_line10))
                                   (if(= int_baseline 0)vec_line0 vec_line1)))
                 p_temp(mapcar '(lambda(a b)(+ a(* d b)))(if(= int_baseline 0)p_line01 p_line10)
                               (if(= int_baseline 0)vec_line0 vec_line1))
                 
                 )

           (setq ls_grdraw(cons(list p_proj p_temp 2)ls_grdraw))
           (grdraw p_proj p_temp 2)
           ;; (grdraw p_center_limit00  p_center_limit01 3)
           ;; (grdraw p_center_limit11  p_center_limit01 1)

           
           (func_insertarc_move p_temp 'ls_arc_temp int_baseline )
           
           (if bool_limit
               (progn
                 
                 (mapcar '(lambda(e lst bool / pc p0 p1 p2 v r d)
                            (mapcar 'set '(pc p0 p1 p2 v)lst)
                            (setq ls_grdraw(cons
                                            (if bool(list p0 p_line01 4)
                                              (list p1 p_line10 4))
                                            ls_grdraw))
                            (setq d(apply '+(mapcar '* v pc)))
                            (make_arcdimension e(list pc p0 p1 p2
                                                      radius_arcmove v d
                                                      " " str_dimstyle_ductlevel))
                            (setq ls_grdraw(cons(list pc p0 8)ls_grdraw))
                            (setq ls_grdraw(cons(list pc p1 8)ls_grdraw))
                            (if(and(= bool_linetype 2)(equal(= int_baseline 0)bool))
                                (mapcar '(lambda(p)
                                           (setq ls_grdraw(cons(list p_temp p 8)ls_grdraw))
                                           )
                                        (list p0 p1)))
                            )
                         (mapcar 'car ls_entna_arctemp) ls_arc_temp(list T nil))
                 

                 (mapcar '(lambda(a)(grdraw(car a)(cadr a)(caddr a)))ls_grdraw)
                 
                 )
             (progn
               
               (mapcar '(lambda(e p bool / pc p0 p1 p2 v r d ls_gcode)
                          (setq ls_gcode(entget e)
                                p0(cdr(assoc(if bool 13 14)ls_gcode))
                                p1(cdr(assoc(if bool 14 13)ls_gcode))
                                pc(cdr(assoc 15 ls_gcode))
                                )
                          (grdraw p0 p 240)
                          (grdraw pc p0 8)
                          (grdraw pc p1 8)
                          )
                       (mapcar 'car ls_entna_arctemp)(list p_line01 p_line10)(list T nil))
               
               )
             
             )
           
           ))
       ))
    
    (cons
     "CLICK"
     (lambda();;gr3

       (if(if point_decide T (setq point_decide ls_arc_temp))
           (progn
             (setq ls_vnam_duct
                   (subst(list(assoc "ARC" ls_currentarc0)
                              (assoc "OBJ" ls_currentarc0)
                              (cons "RADIUS" radius_arcmove)
                              (cons "POSITION" point_decide)
                              )
                         ls_currentarc0 ls_vnam_duct)
                   ls_vnam_duct
                   (subst(list(assoc "ARC" ls_currentarc1)
                              (assoc "OBJ" ls_currentarc1)
                              (cons "RADIUS" radius_arcmove)
                              (cons "POSITION" point_decide)
                              )
                         ls_currentarc1 ls_vnam_duct)
                   )
             
             (mapcar '(lambda(v)
                        (setq v(cadr v))
                        (exckillobj v)
                        (vla-delete v))
                     ls_entna_arctemp)
             
             
             (setq bool_replacegrread T int_grread 3 
                   bool_noeditdepth T str_edit "makeductmain"
                   str_editreturn "insertarc"
                   p_arcprev nil
                   )
             )
         (progn
           (x-alert(list 20870 24359 12364 34920 31034 12373 12428 12390 12356 12394 12356 29366 24907 12391 12398 12463 12522 12483 12463 12399 28961 21177 12391 12377 ))
           ;;円弧が表示されていない状態でのクリックは無効です
           )
         )
       
       
       ))
    ;;KEYBOAD
    )

   (list
    "makeccboxmain" ;;edsym
    (cons
     "INITIAL"
     (lambda(bool);;initial
       (if(car bool)
           (progn
             ;;temp
             
             (setq bool_point nil
                   bool_selectent nil bool_select nil int_selectmode -1
                   ls_ssget nil xtype_ssget nil xdata_ssget nil
                   ;;ls_ssgetを変えるときは注意
                   )
             
             (setq
              func_guidemenu
              (lambda()
                (mix_strasc
                 (list )
                 ) )
              
              ls_guideexplane
              (mapcar
               'mix_strasc
               (list ))

              ls_guidemenu
              (list
               
               (list(list 49);;テンプレートから特殊部作成
                    (cons "ITEM"(list 12486 12531 12503 12524 12540 12488 12363 12425 29305 27530 37096 20316 25104   ))
                    (cons "NEXTMODE" "makeccbox-temp")
                    (cons "HELP"(lambda()(mix_strasc(list  ))))
                    )

               (list(list 50);;テンプレートからマンホール作成
                    (cons "ITEM"(list 12486 12531 12503 12524 12540 12488 12363 12425 12510 12531 12507 12540 12523 20316 25104   ))
                    (cons "NEXTMODE" "makemanhole-temp")
                    (cons "HELP"(lambda()(mix_strasc(list  ))))
                    )

               
               (list(list 51);;平面図から特殊部マンホール作成
                    (cons "ITEM"(list 24179 38754 22259 12363 12425 29305 27530 37096 12510 12531 12507 12540 12523  20316 25104   ))
                    (cons "NEXTMODE" "makeccbox-plane")
                    (cons "HELP"(lambda()(mix_strasc(list  ))))
                    )
               

               (list(list "ENTER");;メインメニューへ
                    (cons "ITEM"(list 12513 12452 12531 12513 12491 12517 12540 12408))
                    ;; (cons "LOADFUNCTION"
                    ;;       (lambda()(setq str_next "home"))
                    ;;       )
                    (cons "NEXTMODE" "home")
                    )
               
               )

              
              
              )
             
             ))

       (if(cadr bool) (list ) )
       ))
    
    
    )

   (list
    "makeccbox-temp" ;;edsym
    (cons
     "INITIAL"
     (lambda(bool);;initial
       (if(car bool)
           (progn
             ;;temp
             (setq bool_point nil
                   bool_selectent nil bool_select nil int_selectmode -1
                   ls_ssget nil xtype_ssget nil xdata_ssget nil
                   ;;ls_ssgetを変えるときは注意
                   )

             (setq str_templateccbox nil
                   length_ccboxplane 0. offset_ccboxplane 0.)
             
             (if bool_tempdistlength
                 (setq bool_tempdistlength nil)
               (setq p_ccbox0 nil p_ccbox1 nil p_ccbox2 nil p_manhole nil
                     p_manhole_edge nil p_manhole_edge1 nil p_manhole_edge2 nil
                     str_colccbox0 91 str_colccbox1 111
                     str_colccbox2 131 str_colmanhole 151 str_colmanhole_edge 171
                     ))
             
             (setq
              func_guidemenu
              (lambda()
                (mix_strasc
                 (list )
                 ) )
              
              
              ls_guideexplane
              (mapcar
               'mix_strasc
               (list))
              
              ls_guidemenu
              (list
               (list(list 76);; 地表面標高
                    (cons "ITEM"(list 22320 34920 38754 27161 39640))
                    (cons "STATUS"
                          (lambda()
                            (if str_lasground
                                (mix_strasc
                                 (list "{\\C" str_gcol_c ";" 12487 12540 12479 "} : "
                                       (vl-string-subst "" "lasgrid-" str_lasground)))
                              (if height_ground
                                  (mix_strasc
                                   (list"{\\C" str_gcol_g ";" 27161 39640 "} : "
                                        (as-numstr height_ground)))
                                (mix_strasc
                                 (list "{\\C" str_gcol_r ";"
                                       36984 25246 12373 12428 12390 12356 12414 12379 12435 "}"))
                                ))
                            ))
                    (cons "LOADFUNCTION"(lambda()(settile_selectground)))
                    (cons "HELP"(lambda()(mix_strasc(list 20351 29992 12377 12427 27161 39640 12434 "\n- las" 35501 36796 "\n- xml" 35501 36796 "\n- " 19968 23450 27161 39640 12398 25968 20516 20837 21147 "\n" 12363 12425 36984 25246 12391 12365 12414 12377 ))))
                    )

               (list(list 67);;特殊部の色
                    (cons "ITEM"(list 29305 27530 37096 12398 33394))
                    (cons "INPUTCOLOR"(lambda()
                                        (if int_colccbox_temp T(setq int_colccbox_temp int_colccbox))
                                        'int_colccbox_temp))
                    (cons "LOADFUNCTION"
                          (lambda()
                            nil
                            ))
                    ;;カラーダイアログが表示され、特殊部のモデルに使う色を選択できます
                    (cons "HELP"(lambda()(mix_strasc(list 12459 12521 12540 12480 12452 12450 12525 12464 12364 34920 31034 12373 12428 12289 29305 27530 37096 12398 12514 12487 12523 12395 20351 12358 33394 12434 36984 25246 12391 12365 12414 12377 ))))
                    )
               
               (list(list 70);;テンプレート選択
                    (cons "ITEM"(list 12486 12531 12503 12524 12540 12488 36984 25246 ))
                    (cons "LOADFUNCTION"
                          (lambda()
                            (td3dtemplate)
                            ))
                    (cons "STATUS"
                          (lambda()
                            (if str_templateccbox str_templateccbox
                              (mix_strasc(list 12394 12375 )))
                            ))
                    )
               
               
               (list(list 69);;E特殊部天端から地表面まで
                    (cons "ITEM"(list 29305 27530 37096 22825 31471 12363 12425 22320 34920 38754 12414 12391))
                    (cons "INPUT"(lambda()
                                   (if height_ccboxtop_temp T
                                     (setq height_ccboxtop_temp height_ccboxtop))
                                   'height_ccboxtop_temp))
                    (cons "LOADFUNCTION"
                          (lambda()nil))
                    ;;特殊部の天端から地表面までの高さで、マンホールを作成するときマンホール高さを表す数値となります
                    (cons "HELP"(lambda()(mix_strasc(list 29305 27530 37096 12398 22825 31471 12363 12425 22320 34920 38754 12414 12391 12398 39640 12373 12391 12289 12510 12531 12507 12540 12523 12434 20316 25104 12377 12427 12392 12365 12510 12531 12507 12540 12523 39640 12373 12434 34920 12377 25968 20516 12392 12394 12426 12414 12377 (if int_selectmenu str_guide_inputval str_guide_selectval)))))
                    )
               
               
               ;; (list(list 87);;W均しコンオフセット
               ;;      (cons "ITEM"(list 22343 12375 12467 12531 12458 12501 12475 12483 12488))
               ;;      (cons "INPUT"(lambda()
               ;;                     (if offset_levelingcon_temp T
               ;;                       (setq offset_levelingcon_temp offset_levelingcon))
               ;;                     'offset_levelingcon_temp))
               ;;      ;;特殊部の全周に入力値を加える
               ;;      (cons "HELP"(lambda()(mix_strasc(list 29305 27530 37096 12398 20840 21608 12395 20837 21147 20516 12434 21152 12360 12427(if int_selectmenu str_guide_inputval str_guide_selectval)))))
               ;;      )
               ;; (list(list 84);;T均しコン高さ
               ;;      (cons "ITEM"(list 22343 12375 12467 12531 39640 12373))
               ;;      (cons "INPUT"(lambda()
               ;;                     (if height_levelingcon_temp T
               ;;                       (setq height_levelingcon_temp height_levelingcon))
               ;;                     'height_levelingcon_temp))
               ;;      (cons "HELP"(lambda()(mix_strasc(list(if int_selectmenu str_guide_inputval str_guide_selectval)))))
               ;;      )
               
               (list(list 49);;特殊部起点を選択
                    (cons "ITEM"(list 29305 27530 37096 32 36215 28857 12434 36984 25246 ))
                    (cons "GETPOINT"(lambda()(list p_ccbox0(itoa str_colccbox0))))
                    (cons "LOADFUNCTION"
                          (lambda(bool)
                            (setq int_selectmenu nil)
                            (if bool(setq p_ccbox0 elem_grread))
                            (setq bool_replacegrread T int_grread 2 elem_grread 50)
                            ))
                    ;;特殊部の点を3つ選択します
                    ;;1点目
                    (cons "HELP"(lambda()(mix_strasc(list  "\n1" 28857 30446 (if int_selectmenu str_guide_point)))))
                    )
               
               (list(list 50);;特殊部辺の端点を選択
                    (cons "ITEM"(list 29305 27530 37096 32 36794 12398 31471 28857 12434 36984 25246  ))
                    (cons "GETPOINT"(lambda()(list p_ccbox1(itoa str_colccbox1))))
                    (cons "LOADFUNCTION"
                          (lambda(bool)
                            (setq int_selectmenu nil)
                            (if bool(setq p_ccbox1 elem_grread))
                            (setq bool_replacegrread T int_grread 2 elem_grread 51)
                            ))
                    (cons "HELP"(lambda()(mix_strasc(list "\n2" 28857 30446 (if int_selectmenu str_guide_point)))))
                    )
               
               (list(list 68);;特殊部の長さ
                    (cons "ITEM"(list 29305 27530 37096 12398 38263 12373 "(" 12463 12522 12483 12463 12395 28310 25312 8658 "0)" ))
                    (cons "INPUT"(lambda() 'length_ccboxplane))
                    ;;数値を入力すると1点目(FIX)から2点目に向けての長さとなる\n負の値を入力して逆方向に作成可能
                    (cons "HELP"(lambda()(mix_strasc(list 25968 20516 12434 20837 21147 12377 12427 12392 "1" 28857 30446 "(FIX)" 12363 12425 "2" 28857 30446 12395 21521 12369 12390 12398 38263 12373 12392 12394 12427 "\n" 36000 12398 20516 12434 20837 21147 12375 12390 36870 26041 21521 12395 20316 25104 21487 33021  (if int_selectmenu str_guide_inputval str_guide_selectval)))))
                    )

               (list(list 87);;軸直角方向ずれ
                    (cons "ITEM"(list 36600 30452 35282 26041 21521 12378 12428  ))
                    (cons "INPUT"(lambda() 'offset_ccboxplane))
                    ;;1点目から2点目に向かって右方向が正値
                    (cons "HELP"(lambda()(mix_strasc(list  "1" 28857 30446 12363 12425 "2" 28857 30446 12395 21521 12363 12387 12390 21491 26041 21521 12364 27491 20516  (if int_selectmenu str_guide_inputval str_guide_selectval)))))
                    )
               
               
               (list(list 78);;特殊部の名称
                    (cons "ITEM"(list 29305 27530 37096 12398 21517 31216))
                    (cons "INPUTSTR"
                          (lambda( / str i bool func)
                            (if(= str_ccboxname "")(setq str_ccboxname nil))
                            (if(if str_ccboxname
                                   (if(= int_allow_overwrite 1) nil
                                     (null
                                      (vl-catch-all-error-p
                                       (vl-catch-all-apply 'vla-Item(list vnam_blocktable str_ccboxname))))
                                     )
                                 T)
                                (progn
                                  (setq str "CCBOX$" i 0 bool T)
                                  (while bool
                                    (setq i(1+ i)
                                          str_ccboxname(strcat str(substr(itoa(+ 1000 i))2))
                                          bool
                                          (null
                                           (vl-catch-all-error-p
                                            (vl-catch-all-apply 'vla-Item(list vnam_blocktable str_ccboxname))))
                                          )
                                    )
                                  ))
                            'str_ccboxname)
                          )
                    (cons "NO-INPUT" (lambda()nil ))
                    (cons "LOADFUNCTION"
                          (lambda(str / bool)
                            (setq bool
                                  (vl-catch-all-error-p
                                   (vl-catch-all-apply 'vla-Item(list vnam_blocktable str)))
                                  )
                            (if bool T
                              (if(= int_allow_overwrite 0)nil
                                (progn
                                  (alert
                                   (mix_strasc(list 26082 12395 23384 22312 12377 12427 12502 12525 12483 12463 21517 31216 12391 12377 12364 19978 26360 12365 12373 12428 12414 12377 ))
                                   )
                                  T)))
                            )
                          )
                    (cons "STRINPUTALERT"
                          (mix_strasc(list 12502 12525 12483 12463 21517 31216 12364 26082 12395 23384 22312 12375 12390 12356 12414 12377 )))
                    
                    ;;これから作成する特殊部、編集中の特殊部管路の名称を変更します\n特殊部はブロックとして作成されすでに使用されているブロック名称は設定できません
                    ;;\n名前を付けないとき「CCBOX$(使用されていない数値)」を自動的に設定します
                    (cons "HELP"(lambda()(mix_strasc(list 12371 12428 12363 12425 20316 25104 12377 12427 29305 27530 37096 12289 32232 38598 20013 12398 29305 27530 37096 31649 36335 12398 21517 31216 12434 22793 26356 12375 12414 12377 "\n" 29305 27530 37096 12399 12502 12525 12483 12463 12392 12375 12390 20316 25104 12373 12428 12377 12391 12395 20351 29992 12373 12428 12390 12356 12427 12502 12525 12483 12463 21517 31216 12399 35373 23450 12391 12365 12414 12379 12435 "\n" 21517 21069 12434 20184 12369 12394 12356 12392 12365 12300 "CCBOX$(" 20351 29992 12373 12428 12390 12356 12394 12356 25968 20516 ")" 12301 12434 33258 21205 30340 12395 35373 23450 12375 12414 12377))))
                    
                    )


               (list(list 80 );;P選択モード切替
                    (cons "ITEM"(list 36984 25246 12514 12540 12489 20999 26367 ))
                    (cons "INPUTSWITCH"
                          (lambda()
                            (setq int_temp 0)
                            (if(= int_ccboxmode 2)
                                (if(= int_selectmode -1)
                                    (list nil(mix_strasc
                                              (list "{\\C" str_gcol_p ";"
                                                    21336 20307 36984 25246 12398 12415 "}")))
                                  (list 'int_selectmode
                                        (mapcar 'mix_strasc
                                                (list(list "{\\C" str_gcol_y ";" 36984 25246 "}")
                                                     (list "{\\C" str_gcol_c ";" 35299 38500 "}")))
                                        ))
                              (list 'int_temp ;;削除モードのとき使用可能
                                    (list(mix_strasc
                                          (list "{\\C" str_gcol_p ";"
                                                21066 38500 12514 12540 12489 12398 12392 12365 20351 29992 21487 33021 "}")))
                                    )
                              )) )
                    (cons "HELP"(lambda()str_guide_selectmode))
                    )
               
               
               
               (list(list "ENTER");;メインメニューへ
                    (cons "ITEM"(list 12513 12452 12531 12513 12491 12517 12540 12408))
                    (cons "LOADFUNCTION"
                          (lambda()
                            (setq str_next
                                  (if(or p_ccbox0 p_ccbox1)
                                      nil "home"))
                            ))
                    (cons "NEXTMODE" "home")
                    )

               )

              ;; bool_replacegrread T int_grread 2 elem_grread 49
              
              
              )
             
             ))
       
       (if(cadr bool) (list ) )
       ))
    
    (cons
     "MOVE"
     (lambda();;gr5

       (mapcar
        '(lambda(p c / s ls_p)
           (if p
               (progn
                 (setq s(* height_text 0.8)
                       ls_p(mapcar
                            '(lambda(xx yy)
                               (mapcar '(lambda(a x y)(+ a(* xx x)(* yy y)))
                                       p vec_x_onview vec_y_onview)
                               )
                            (list s(- s)(- s)s) (list s(- s)s(- s)))
                       )
                 (mapcar '(lambda(p0 p1)(grdraw p0 p1 c))
                         (list(car ls_p)(caddr ls_p))
                         (list(cadr ls_p)(cadddr ls_p)))
                 ))
           )
        (list p_ccbox0 p_ccbox1 )
        (list str_colccbox0 str_colccbox1 )
        )

       (if(and p_ccbox0(null p_ccbox1)bool_point)(grdraw p_ccbox0 elem_grread 2))
       
       ))
    
    (cons
     "CLICK"
     (lambda( / )
       (cond
        ((if(if(= int_ccboxmode 1)
                (if(setq set_ent(ssget elem_grread(list(cons 0 "INSERT")(list -3(list "terraduct3d")))))
                    (setq vnam(vlax-ename->vla-object(ssname set_ent 0)))))
             (progn
               (vla-getXData vnam "terraduct3d" 'array_Type 'array_Data )
               (setq ls_xdata
                     (if array_data
                         (split_list 0(mapcar 'vlax-variant-value
                                              (vlax-safearray->list array_data))))
                     )
               
               (=(cdr(assoc "terraduct3d" ls_xdata))"CCBOXBLOCK")
               ))
         
         (setq str_bname(vla-get-name vnam)
               block(vl-catch-all-apply 'vla-Item(list vnam_blocktable str_bname)))
         

         (settile_strinput;;名称変更
          'str_bname
          (lambda(a)
            (if(= a str_bname)T
              (vl-catch-all-error-p
               (vl-catch-all-apply 'vla-Item(list vnam_blocktable a))))
            )
          
          (mix_strasc(list 21517 31216 22793 26356 ))
          (mix_strasc(list 26082 12395 23384 22312 12377 12427 21517 31216 12399 20351 12360 12414 12379 12435 ))
          ;;既に存在する名称は使えません
          )
         
         (if(if str_bname(/= str_bname ""))(vla-put-name block str_bname))

         
         (mapcar '(lambda(v)
                    (vlax-release-object v)
                    (setq ls_vla-release(vl-remove v ls_vla-release))
                    )
                 (list block))
         )
        )
       )
     )
    
    ;;  (lambda()nil ))

    (cons
     "KEYBOAD"
     (lambda( / ls_p w h ttop tbot tside hu hv du dv tfr tbk int_col)
       (cond
        ((and(or(= elem_grread 13)(= int_grread 25))
             (= int_ccboxmode 2))
         
         (mapcar
          '(lambda(vnam)
             (if(vlax-erased-p vnam)T
               (progn
                 (setq str(vla-get-name vnam))
                 (if(setq set_ent(ssget "X"(list(cons 2 str))))
                     (progn
                       (setq num(sslength set_ent))
                       (while(>(setq num(1- num))-1)
                         (setq vnam(vlax-ename->vla-object(ssname set_ent num))
                               ls_vnam_highlight(vl-remove vnam ls_vnam_highlight))
                         
                         (vla-delete vnam)
                         )
                       ))
                 (vla-delete
                  (vla-Item(vla-get-Blocks(vla-get-ActiveDocument
                                           (vlax-get-acad-object)))
                           str) )

                 ))
             )
          ls_vnam_select)
         
         )
        ((and(or(= elem_grread 13)(= int_grread 25))
             p_ccbox0 p_ccbox1 str_templateccbox)

         
         (setq str_name str_templateccbox ls_val(td3d_tmp_read str_name)
               ;; (setq str_name(car lst) ls_val(td3d_tmp_fill(cadr lst))
               height_top height_ccboxtop_temp height_base height_ground)
         
         (mapcar 'set '(w h ttop tbot tside hu hv du dv tfr tbk)ls_val)
         
         (setq p_ccbox0(carxyz p_ccbox0 0.)p_ccbox1(carxyz p_ccbox1 0.)
               vec(unit_vector(mapcar '- p_ccbox1 p_ccbox0)))
         (if(= offset_ccboxplane 0.)T
           (setq p_ccbox0(mapcar '(lambda(a b)(+ a(* offset_ccboxplane b)))
                                 p_ccbox0(list(cadr vec)(-(car vec))0.))
                 p_ccbox1(mapcar '(lambda(a b)(+ a(* offset_ccboxplane b)))
                                 p_ccbox1(list(cadr vec)(-(car vec))0.))
                 ))
         
         (if(= length_ccboxplane 0.)T
           (progn
             (setq p_ccbox1(mapcar '(lambda(a b)(+ a(* b length_ccboxplane)))p_ccbox0 vec))
             (if(< length_ccboxplane 0)(setq vec(mapcar '- vec)))
             ))
         
         (setq p_mid(mapcar '(lambda(a b)(* 0.5(+ a b)))p_ccbox0 p_ccbox1)
               length_sld(distance p_ccbox0 p_ccbox1))
         
         (setq ls_p(project_to_ground
                    (mapcar '(lambda(i)(mapcar '(lambda(a b)(* 0.1(+(* (- 10 i)a)(* i b))))
                                               p_ccbox0 p_ccbox1)
                               )
                            (inclist 0 11))
                    (list 0. 0. 1.)
                    (list str_lasground height_ground))
               ls_p(vl-remove nil ls_p)
               )
         
         (cond
          (ls_p
           ;;--- 地表面標高 ---
           (setq elevation_ground
                 (/(apply '+(mapcar 'caddr ls_p))(length ls_p))
                 elevation_bottom
                 (- elevation_ground height_top(+ h ttop tbot))
                 p_center_bottom(carxyz p_mid elevation_bottom))

           ;;--- 部材の作成 ---
           (setq ls_part(td3d_tmp_makeparts ls_val p_center_bottom vec length_sld(getvar "CLAYER")))
           (cond
            ((null ls_part)
             (td3d_tmp_alert (mix_strasc(list 24418 29366 12398 20316 25104 12395 22833 25943 12375 12414 12375 12383 "\n" 12486 12531 12503 12524 12540 12488 12398 23544 27861 12434 35211 30452 12375 12390 12367 12384 12373 12356))))
            (T
             ;;色と xdata を部材ごとに付ける
             (setq int_col(if(and(boundp 'int_colccbox)int_colccbox)int_colccbox 8))
             (mapcar
              '(lambda(a / vna str_part)
                 (setq vna(car a) str_part(cdr a))
                 (vl-catch-all-apply 'vla-put-color(list vna int_col))
                 ;;既存の集計処理が拾えるよう先頭は CCBOXSOLID にする
                 (set_xda vna
                          (list(cons 1000 "CCBOXTEMPSOLID")
                               (cons 1000 "PART")(cons 1000 str_part)
                               (cons 1000 "TEMPLATE")(cons 1000 str_name))
                          "terraduct3d"))
              ls_part)

             ;;--- ブロック化 ---
             (setq blocks(vla-get-Blocks
                          (vla-get-ActiveDocument(vlax-get-acad-object)))
                   ii 0 bool T)
             (while bool
               (setq str_bname(strcat td3d_tmp_ccboxhead
                                      (substr(itoa(+ 1000 ii))2)))
               (if(vl-catch-all-error-p
                   (vl-catch-all-apply 'vla-Item(list blocks str_bname)))
                   (setq bool nil)
                 (setq ii(1+ ii))))

             (setq blk(vla-Add blocks(vlax-3d-point 0 0 0)str_bname))
             (td3d_tmp_copyparts ls_part blk)
             (td3d_tmp_deleteparts ls_part)

             (setq vnam(vla-InsertBlock
                        (vla-get-ModelSpace
                         (vla-get-ActiveDocument(vlax-get-acad-object)))
                        (vlax-3d-point 0 0 0)str_bname 1 1 1 0))

             ;;テンプレート名と全寸法はブロック側に記録する
             (set_xda vnam
                      (append
                       (list(cons 1000 "CCBOXTEMPBLOCK")
                            (cons 1000 "TEMPLATE")(cons 1000 str_name)
                            (cons 1000 "PROJECT-D")
                            (cons 1000(if str_ground str_ground ""))
                            (cons 1000 "PROJECT-H")
                            (cons 1040(if height_base height_base 0.))
                            (cons 1000 "LENGTH")(cons 1040 length_sld)
                            ;;CSV/IFC で同じ形を作り直すために配置そのものも残す
                            ;;  BASE-* は makeparts に渡した底版下面の中心
                            ;;  VEC-* は進行方向(水平の単位ベクトル)
                            (cons 1000 "BASE-X")(cons 1040(car p_center_bottom))
                            (cons 1000 "BASE-Y")(cons 1040(cadr p_center_bottom))
                            (cons 1000 "BASE-Z")(cons 1040(caddr p_center_bottom))
                            (cons 1000 "VEC-X")(cons 1040(car vec))
                            (cons 1000 "VEC-Y")(cons 1040(cadr vec))
                            ;;地表面標高。refreshground はこれとの差だけ上下に動かす
                            ;;(土被りをそのまま保つ)
                            (cons 1000 "GROUND-Z")(cons 1040 elevation_ground))
                       (apply 'append
                              (mapcar '(lambda(lst val)
                                         (list(cons 1000(car lst))(cons 1040 val)))
                                      (td3d_tmp_paramdef)ls_val)))
                      "terraduct3d")

             (vl-catch-all-apply 'vlax-release-object(list blk))
             (princ (mix_strasc(list "\n" 20316 25104 12375 12414 12375 12383 " : " str_bname " (" str_name ") L=" (td3d_tmp_numstr length_sld))))
             ))
           )
          
          
          
          (T
           (x-alert(list 36984 25246 12375 12383 28857 12363 12425 27161 39640 12364 21462 24471 12391 12365 12414 12379 12435 ))
           ;;選択した点から標高が取得できません
           )
          )
         
         
         (setq p_ccbox0 nil p_ccbox1 nil )
         )
        ((and(or(= elem_grread 13)(= int_grread 25))
             (or str_lasground height_ground))
         (x-alert(list 28857 12398 36984 25246 12364 36275 12426 12414 12379 12435 ))
         ;;点の選択が足りません
         )
        ((and(or(= elem_grread 13)(= int_grread 25)))
         (x-alert(list 22320 34920 38754 12398 36984 25246 12364 12354 12426 12414 12379 12435 ))
         ;;地表面の選択がありません
         )
        )
       
       ))
    
    
    )

   
   (list
    "makemanhole-temp" ;;edsym
    (cons
     "INITIAL"
     (lambda(bool);;initial
       (if(car bool)
           (progn
             ;;temp
             (setq bool_point nil
                   bool_selectent nil bool_select nil int_selectmode -1
                   ls_ssget nil xtype_ssget nil xdata_ssget nil
                   ;;ls_ssgetを変えるときは注意
                   )

             (setq str_templatemanhole nil
                   depth_manhole 0.
                   length_ccboxplane 0. offset_ccboxplane 0.)
             
             (if bool_tempdistlength
                 (setq bool_tempdistlength nil)
               (setq p_ccbox0 nil p_ccbox1 nil p_ccbox2 nil p_manhole nil
                     p_manhole_edge nil p_manhole_edge1 nil p_manhole_edge2 nil
                     str_colccbox0 91 str_colccbox1 111
                     str_colccbox2 131 str_colmanhole 151 str_colmanhole_edge 171
                     ))
             
             (setq
              func_guidemenu
              (lambda()
                (mix_strasc
                 (list )
                 ) )
              
              
              ls_guideexplane
              (mapcar
               'mix_strasc
               (list))
              
              ls_guidemenu
              (list
               (list(list 76);; 地表面標高
                    (cons "ITEM"(list 22320 34920 38754 27161 39640))
                    (cons "STATUS"
                          (lambda()
                            (if str_lasground
                                (mix_strasc
                                 (list "{\\C" str_gcol_c ";" 12487 12540 12479 "} : "
                                       (vl-string-subst "" "lasgrid-" str_lasground)))
                              (if height_ground
                                  (mix_strasc
                                   (list"{\\C" str_gcol_g ";" 27161 39640 "} : "
                                        (as-numstr height_ground)))
                                (mix_strasc
                                 (list "{\\C" str_gcol_r ";"
                                       36984 25246 12373 12428 12390 12356 12414 12379 12435 "}"))
                                ))
                            ))
                    (cons "LOADFUNCTION"(lambda()(settile_selectground)))
                    (cons "HELP"(lambda()(mix_strasc(list 20351 29992 12377 12427 27161 39640 12434 "\n- las" 35501 36796 "\n- xml" 35501 36796 "\n- " 19968 23450 27161 39640 12398 25968 20516 20837 21147 "\n" 12363 12425 36984 25246 12391 12365 12414 12377 ))))
                    )

               (list(list 67);;特殊部の色
                    (cons "ITEM"(list 29305 27530 37096 12398 33394))
                    (cons "INPUTCOLOR"(lambda()
                                        (if int_colccbox_temp T(setq int_colccbox_temp int_colccbox))
                                        'int_colccbox_temp))
                    (cons "LOADFUNCTION"
                          (lambda()
                            nil
                            ))
                    ;;カラーダイアログが表示され、特殊部のモデルに使う色を選択できます
                    (cons "HELP"(lambda()(mix_strasc(list 12459 12521 12540 12480 12452 12450 12525 12464 12364 34920 31034 12373 12428 12289 29305 27530 37096 12398 12514 12487 12523 12395 20351 12358 33394 12434 36984 25246 12391 12365 12414 12377 ))))
                    )
               
               (list(list 70);;テンプレート選択
                    (cons "ITEM"(list 12486 12531 12503 12524 12540 12488 36984 25246 ))
                    (cons "LOADFUNCTION"
                          (lambda()
                            (td3dmanhole)
                            ))
                    (cons "STATUS"
                          (lambda()
                            (if str_templatemanhole str_templatemanhole
                              (mix_strasc(list 12394 12375 )))
                            ))
                    )
               
               
               (list(list 69);;E特殊部天端から地表面まで
                    (cons "ITEM"(list 29305 27530 37096 22825 31471 12363 12425 22320 34920 38754 12414 12391))
                    (cons "INPUT"(lambda()
                                   (if height_ccboxtop_temp T
                                     (setq height_ccboxtop_temp height_ccboxtop))
                                   'height_ccboxtop_temp))
                    (cons "LOADFUNCTION"
                          (lambda()nil))
                    ;;特殊部の天端から地表面までの高さで、マンホールを作成するときマンホール高さを表す数値となります
                    (cons "HELP"(lambda()(mix_strasc(list 29305 27530 37096 12398 22825 31471 12363 12425 22320 34920 38754 12414 12391 12398 39640 12373 12391 12289 12510 12531 12507 12540 12523 12434 20316 25104 12377 12427 12392 12365 12510 12531 12507 12540 12523 39640 12373 12434 34920 12377 25968 20516 12392 12394 12426 12414 12377 (if int_selectmenu str_guide_inputval str_guide_selectval)))))
                    )
               
               
               (list(list 49);;マンホール中心
                    (cons "ITEM"(list 12510 12531 12507 12540 12523 20013 24515   ))
                    (cons "GETPOINT"(lambda()(list p_ccbox0(itoa str_colccbox0))))
                    (cons "LOADFUNCTION"
                          (lambda(bool)
                            (setq int_selectmenu nil)
                            
                            (if bool(setq p_ccbox0(car(project_to_ground
                                                       (list elem_grread)
                                                       (list 0. 0. 1.) (list str_lasground height_ground)))
                                          ))
                            (if p_ccbox0
                                (setq bool_replacegrread T int_grread 2 elem_grread 51)

                              (x-alert(list 36984 25246 12375 12383 28857 12363 12425 27161 39640 12364 21462 24471 12391 12365 12414 12379 12435 ))
                              ;;選択した点から標高が取得できません
                              
                              )
                            
                            ))
                    ;;マンホールの中心を選択してください
                    (cons "HELP"(lambda()(mix_strasc(list 12510 12531 12507 12540 12523 12398 20013 24515 12434 36984 25246 12375 12390 12367 12384 12373 12356  (if int_selectmenu str_guide_point)))))
                    )
               
               (list(list 50);;偏心の方向
                    (cons "ITEM"(list 20559 24515 12398 26041 21521  ))
                    (cons "GETPOINT"(lambda()(list p_ccbox1(itoa str_colccbox1))))
                    (cons "LOADFUNCTION"
                          (lambda(bool)
                            (setq int_selectmenu nil)
                            (if bool(setq p_ccbox1 elem_grread))
                            (setq bool_replacegrread T int_grread 2 elem_grread 52)
                            ))
                    ;;偏心があるテンプレートを選んだときのみ有効
                    (cons "HELP"(lambda()(mix_strasc(list 20559 24515 12364 12354 12427 12486 12531 12503 12524 12540 12488 12434 36984 12435 12384 12392 12365 12398 12415 26377 21177 (if int_selectmenu str_guide_point)))))
                    )

               (list(list 51);;マンホールの下端を点で選択(Zのみ参照)
                    (cons "ITEM"(list 12510 12531 12507 12540 12523 12398 19979 31471 12434 28857 12391 36984 25246
                                      "(Z" 12398 12415 21442 29031 ")" ))
                    (cons "GETPOINT"(lambda()(list p_ccbox2(itoa str_colccbox2))))
                    (cons "LOADFUNCTION"
                          (lambda(bool)
                            (setq int_selectmenu nil)
                            (if bool(setq p_ccbox2 elem_grread))
                            (setq bool_replacegrread T int_grread 2 elem_grread 52)
                            ))
                    ;;マンホールの下端に当たる箇所を選択します\nマンホール高さは「点選択＞高さ入力＞テンプレートに書かれた高さ」の順で優先されます
                    (cons "HELP"(lambda()(mix_strasc(list 12510 12531 12507 12540 12523 12398 19979 31471 12395 24403 12383 12427 31623 25152 12434 36984 25246 12375 12414 12377 "\n" 12510 12531 12507 12540 12523 39640 12373 12399 12300 28857 36984 25246 65310 39640 12373 20837 21147 65310 12486 12531 12503 12524 12540 12488 12395 26360 12363 12428 12383 39640 12373 12301 12398 38918 12391 20778 20808 12373 12428 12414 12377  (if int_selectmenu str_guide_point)))))
                    )
               
               
               (list(list 68);;マンホール高さ
                    (cons "ITEM"(list 12510 12531 12507 12540 12523 39640 12373 ))
                    (cons "INPUT"(lambda() 'depth_manhole))
                    ;;0のとき無効\nマンホール高さは「点選択＞高さ入力＞テンプレートに書かれた高さ」の順で優先されます
                    (cons "HELP"(lambda()(mix_strasc(list "0" 12398 12392 12365 28961 21177 "\n" 12510 12531 12507 12540 12523 39640 12373 12399 12300 28857 36984 25246 65310 39640 12373 20837 21147 65310 12486 12531 12503 12524 12540 12488 12395 26360 12363 12428 12383 39640 12373 12301 12398 38918 12391 20778 20808 12373 12428 12414 12377  (if int_selectmenu str_guide_inputval str_guide_selectval)))))
                    )

               (list(list 78);;マンホールの名称
                    (cons "ITEM"(list 12510 12531 12507 12540 12523 12398 21517 31216 ))
                    (cons "INPUTSTR"
                          (lambda( / str i bool func)
                            (if(= str_ccboxname "")(setq str_ccboxname nil))
                            (if(if str_ccboxname
                                   (if(= int_allow_overwrite 1) nil
                                     (null
                                      (vl-catch-all-error-p
                                       (vl-catch-all-apply 'vla-Item(list vnam_blocktable str_ccboxname))))
                                     )
                                 T)
                                (progn
                                  (setq str "MANHOLE$" i 0 bool T)
                                  (while bool
                                    (setq i(1+ i)
                                          str_ccboxname(strcat str(substr(itoa(+ 1000 i))2))
                                          bool
                                          (null
                                           (vl-catch-all-error-p
                                            (vl-catch-all-apply 'vla-Item(list vnam_blocktable str_ccboxname))))
                                          )
                                    )
                                  ))
                            'str_ccboxname)
                          )
                    (cons "NO-INPUT" (lambda()nil ))
                    (cons "LOADFUNCTION"
                          (lambda(str / bool)
                            (setq bool
                                  (vl-catch-all-error-p
                                   (vl-catch-all-apply 'vla-Item(list vnam_blocktable str)))
                                  )
                            (if bool T
                              (if(= int_allow_overwrite 0)nil
                                (progn
                                  (alert
                                   (mix_strasc(list 26082 12395 23384 22312 12377 12427 12502 12525 12483 12463 21517 31216 12391 12377 12364 19978 26360 12365 12373 12428 12414 12377 ))
                                   )
                                  T)))
                            )
                          )
                    (cons "STRINPUTALERT"
                          (mix_strasc(list 12502 12525 12483 12463 21517 31216 12364 26082 12395 23384 22312 12375 12390 12356 12414 12377 )))
                    
                    ;;これから作成するマンホール、編集中のマンホールの名称を変更します\nマンホールはブロックとして作成されすでに使用されているブロック名称は設定できません
                    ;;\n名前を付けないとき「CCBOX$(使用されていない数値)」を自動的に設定します
                    (cons "HELP"(lambda()(mix_strasc(list 12371 12428 12363 12425 20316 25104 12377 12427 12510 12531 12507 12540 12523  12289 32232 38598 20013 12398
                                                          12510 12531 12507 12540 12523 31649 36335 12398 21517 31216 12434 22793 26356 12375 12414 12377
                                                          "\n"  12510 12531 12507 12540 12523  12399 12502 12525 12483 12463 12392 12375 12390 20316 25104 12373 12428 12377 12391 12395 20351 29992 12373 12428 12390 12356 12427 12502 12525 12483 12463 21517 31216 12399 35373 23450 12391 12365 12414 12379 12435 "\n" 21517 21069 12434 20184 12369 12394 12356 12392 12365 12300 "MANHOLE$(" 20351 29992 12373 12428 12390 12356 12394 12356 25968 20516 ")" 12301 12434 33258 21205 30340 12395 35373 23450 12375 12414 12377))))
                    
                    )

               (list(list 80 );;P選択モード切替
                    (cons "ITEM"(list 36984 25246 12514 12540 12489 20999 26367 ))
                    (cons "INPUTSWITCH"
                          (lambda()
                            (setq int_temp 0)
                            (if(= int_ccboxmode 2)
                                (if(= int_selectmode -1)
                                    (list nil(mix_strasc
                                              (list "{\\C" str_gcol_p ";"
                                                    21336 20307 36984 25246 12398 12415 "}")))
                                  (list 'int_selectmode
                                        (mapcar 'mix_strasc
                                                (list(list "{\\C" str_gcol_y ";" 36984 25246 "}")
                                                     (list "{\\C" str_gcol_c ";" 35299 38500 "}")))
                                        ))
                              (list 'int_temp ;;削除モードのとき使用可能
                                    (list(mix_strasc
                                          (list "{\\C" str_gcol_p ";"
                                                21066 38500 12514 12540 12489 12398 12392 12365 20351 29992 21487 33021 "}")))
                                    )
                              )) )
                    (cons "HELP"(lambda()str_guide_selectmode))
                    )
               
               
               
               (list(list "ENTER");;メインメニューへ
                    (cons "ITEM"(list 12513 12452 12531 12513 12491 12517 12540 12408))
                    (cons "LOADFUNCTION"
                          (lambda()
                            (setq str_next
                                  (if(or p_ccbox0 p_ccbox1 p_ccbox2)
                                      nil "home"))
                            ))
                    (cons "NEXTMODE" "home")
                    )

               )

              ;; bool_replacegrread T int_grread 2 elem_grread 49
              
              
              )
             
             ))
       
       (if(cadr bool) (list ) )
       ))
    
    (cons
     "MOVE"
     (lambda();;gr5

       (mapcar
        '(lambda(p c / s ls_p)
           (if p
               (progn
                 (setq s(* height_text 0.8)
                       ls_p(mapcar
                            '(lambda(xx yy)
                               (mapcar '(lambda(a x y)(+ a(* xx x)(* yy y)))
                                       p vec_x_onview vec_y_onview)
                               )
                            (list s(- s)(- s)s) (list s(- s)s(- s)))
                       )
                 (mapcar '(lambda(p0 p1)(grdraw p0 p1 c))
                         (list(car ls_p)(caddr ls_p))
                         (list(cadr ls_p)(cadddr ls_p)))
                 ))
           )
        (list p_ccbox0 p_ccbox1 )
        (list str_colccbox0 str_colccbox1 )
        )

       (if(and p_ccbox0(= int_selectmenu 6))
           (grdraw p_ccbox0(carxyz p_ccbox0(caddr elem_grread))2))
       
       ))
    
    (cons
     "CLICK"
     (lambda( / )
       (cond
        ((if(if(= int_ccboxmode 1)
                (if(setq set_ent(ssget elem_grread(list(cons 0 "INSERT")(list -3(list "terraduct3d")))))
                    (setq vnam(vlax-ename->vla-object(ssname set_ent 0)))))
             (progn
               (vla-getXData vnam "terraduct3d" 'array_Type 'array_Data )
               (setq ls_xdata
                     (if array_data
                         (split_list 0(mapcar 'vlax-variant-value
                                              (vlax-safearray->list array_data))))
                     )
               
               (=(cdr(assoc "terraduct3d" ls_xdata))"CCBOXBLOCK")
               ))
         
         (setq str_bname(vla-get-name vnam)
               block(vl-catch-all-apply 'vla-Item(list vnam_blocktable str_bname)))
         

         (settile_strinput;;名称変更
          'str_bname
          (lambda(a)
            (if(= a str_bname)T
              (vl-catch-all-error-p
               (vl-catch-all-apply 'vla-Item(list vnam_blocktable a))))
            )
          
          (mix_strasc(list 21517 31216 22793 26356 ))
          (mix_strasc(list 26082 12395 23384 22312 12377 12427 21517 31216 12399 20351 12360 12414 12379 12435 ))
          ;;既に存在する名称は使えません
          )
         
         (if(if str_bname(/= str_bname ""))(vla-put-name block str_bname))

         
         (mapcar '(lambda(v)
                    (vlax-release-object v)
                    (setq ls_vla-release(vl-remove v ls_vla-release))
                    )
                 (list block))
         )
        )
       )
     )
    
    ;;  (lambda()nil ))

    (cons
     "KEYBOAD"
     (lambda( / ls_p w h ttop tbot tside hu hv du dv tfr tbk int_col)
       (cond
        ((and(or(= elem_grread 13)(= int_grread 25))
             (= int_ccboxmode 2))
         
         (mapcar
          '(lambda(vnam)
             (if(vlax-erased-p vnam)T
               (progn
                 (setq str(vla-get-name vnam))
                 (if(setq set_ent(ssget "X"(list(cons 2 str))))
                     (progn
                       (setq num(sslength set_ent))
                       (while(>(setq num(1- num))-1)
                         (setq vnam(vlax-ename->vla-object(ssname set_ent num))
                               ls_vnam_highlight(vl-remove vnam ls_vnam_highlight))
                         
                         (vla-delete vnam)
                         )
                       ))
                 (vla-delete
                  (vla-Item(vla-get-Blocks(vla-get-ActiveDocument
                                           (vlax-get-acad-object)))
                           str) )

                 ))
             )
          ls_vnam_select)
         
         )
        
        ((if(and(or(= elem_grread 13)(= int_grread 25))
                p_ccbox0 str_templatemanhole)
             (progn
               (setq str_name str_templatemanhole
                     ls_val(td3d_mh_fill(td3d_mh_read str_name))
                     elevation_ground(caddr p_ccbox0)
                     )

               (if(td3d_mh_needdirp ls_val)
                   (if p_ccbox1(>(distance(carxy p_ccbox0)(carxy p_ccbox1))1e-8)
                     (progn;;偏心があるものを選択したので返信方向の選択が必要です
                       (x-alert(list  20559 24515 12364 12354 12427 12418 12398 12434 36984 25246 12375 12383 12398 12391 36820 20449 26041 21521 12398 36984 25246 12364 24517 35201 12391 12377 ))
                       nil)
                     )
                 T)
               
               )
           )
         
         (setq height_all;;全長
               (if p_ccbox2(abs(- elevation_ground(caddr p_ccbox2)))
                 (if(= depth_manhole 0.)nil(abs depth_manhole)))
               height_base height_ground
               p0(carxyz p_ccbox0 0.) p1(if p_ccbox1(carxyz p_ccbox1 0.))
               )
         
         ;;vecu はローカル宣言されていないので、前回の向きが残らないよう毎回入れ直す
         ;;  nil のとき makeparts は X 方向として扱う
         (setq vecu(if p1(unit_vector(mapcar '- p1 p0))))

         (setq p_top(carxyz p0 elevation_ground)
               ls_part(td3d_mh_makeparts ls_val p_top vecu height_all (getvar "CLAYER")))

         
         (setq int_col(if(and(boundp 'int_colccbox)int_colccbox)int_colccbox 8))
         (mapcar
          '(lambda(a / vna str_part)
             (setq vna(car a) str_part(cdr a))
             ;;鉄蓋だけは色251で固定する
             (vl-catch-all-apply
              'vla-put-color
              (list vna(if(= str_part "MHCOVER")td3d_mh_covercolor int_col)))
             (set_xda vna
                      (list(cons 1000 "MANHOLESOLID")
                           (cons 1000 "PART")(cons 1000 str_part)
                           (cons 1000 "TEMPLATE")(cons 1000 str_name))
                      "terraduct3d"))
          ls_part)
         
         ;;ブロック化
         (setq blocks(vla-get-Blocks
                      (vla-get-ActiveDocument(vlax-get-acad-object)))
               ii 0 bool T)
         (while bool
           (setq str_bname(strcat td3d_mh_mhhead(substr(itoa(+ 1000 ii))2)))
           (if(vl-catch-all-error-p
               (vl-catch-all-apply 'vla-Item(list blocks str_bname)))
               (setq bool nil)
             (setq ii(1+ ii))))
         (setq blk(vla-Add blocks(vlax-3d-point 0 0 0)str_bname))
         (td3d_mh_copyparts ls_part blk)
         (td3d_mh_deleteparts ls_part)
         (setq vnam(vla-InsertBlock
                    (vla-get-ModelSpace
                     (vla-get-ActiveDocument(vlax-get-acad-object)))
                    (vlax-3d-point 0 0 0)str_bname 1 1 1 0))
         (set_xda vnam
                  (append
                   (list(cons 1000 "MANHOLEBLOCK")
                        (cons 1000 "TEMPLATE")(cons 1000 str_name)
                        (cons 1000 "PROJECT-D")
                        (cons 1000(if str_ground str_ground ""))
                        (cons 1000 "PROJECT-H")
                        (cons 1040(if height_base height_base 0.))
                        (cons 1000 "CENTER-X")(cons 1040(car p0))
                        (cons 1000 "CENTER-Y")(cons 1040(cadr p0))
                        (cons 1000 "TOPZ")(cons 1040 elevation_ground)
                        ;;CSV/IFC で同じ形を作り直すために向きと総高さも残す
                        ;;  VEC-* は角形・偏心のときの向き(未指定なら X 方向)
                        ;;  TOTALH は 0 のときテンプレートの合計高さをそのまま使う
                        (cons 1000 "VEC-X")(cons 1040(if vecu(car vecu)1.))
                        (cons 1000 "VEC-Y")(cons 1040(if vecu(cadr vecu)0.))
                        (cons 1000 "TOTALH")
                        (cons 1040(if height_all height_all 0.)))
                   (apply 'append
                          (mapcar '(lambda(lst val)
                                     (list(cons 1000(car lst))(cons 1040 val)))
                                  (td3d_mh_paramdef)ls_val)))
                  "terraduct3d")
         (vl-catch-all-apply 'vlax-release-object(list blk))
         
         
         (setq p_ccbox0 nil p_ccbox1 nil p_ccbox2 nil )
         )
        ((and(or(= elem_grread 13)(= int_grread 25)))
         (x-alert(list 22320 34920 38754 12398 36984 25246 12364 12354 12426 12414 12379 12435 ))
         ;;地表面の選択がありません
         )
        )
       
       ))
    
    
    )
   


   
   (list
    "makeccbox-plane" ;;edsym
    (cons
     "INITIAL"
     (lambda(bool);;initial
       (if(car bool)
           (progn
             ;;temp
             (setq bool_point T
                   bool_selectent nil bool_select nil int_selectmode -1
                   ls_ssget nil xtype_ssget nil xdata_ssget nil
                   )


             (if bool_tempdistlength
                 (setq bool_tempdistlength nil)
               (setq p_ccbox0 nil p_ccbox1 nil p_ccbox2 nil p_manhole nil
                     p_manhole_edge nil p_manhole_edge1 nil p_manhole_edge2 nil
                     str_colccbox0 91 str_colccbox1 111
                     str_colccbox2 131 str_colmanhole 151 str_colmanhole_edge 171
                     ))
             
             (setq
              func_guidemenu
              (lambda()
                (mix_strasc
                 (list )
                 ) )
              
              
              ls_guideexplane
              (mapcar
               'mix_strasc
               (list(list " - " 24179 38754 24418 29366 12434 12463 12522 12483 12463 12391 27770 23450 12377 12427)
                    (list " - " 24179 38754 24418 29366 12399 24517 12378 38263 26041 24418 12392 12394 12426 12289)
                    (list "   3" 28857 30446 12399 "1,2" 28857 30446 12392 24179 34892 12394 30452 32218 19978 12398 20219 24847 12398 28857 12434 36984 25246 12375 12390 12424 12356 )
                    (list " - " 12510 12531 12507 12540 12523 12399 20870 21608 19978 12398 "3" 28857 36984 25246 12363 12289 20013 24515 36984 25246 12392 30452 24452 20837 21147 12391 20316 25104 12377 12427  )
                    (list " - " 12356 12378 12428 12418 12394 12356 12392 12365 20316 25104 12373 12428 12378 12289 20001 26041 36984 25246 12375 12383 12392 12365 20013 24515 12434 20778 20808 12377 12427 )
                    
                    ))
              ;;平面形状をクリックで決定する
              ;;平面形状は必ず長方形となり、3点目は1,2点目と平行な直線上の任意の点を選択してよい
              ;;マンホールは円周上の3点選択か、中心選択と直径入力で作成する
              ;;いずれもないとき作成されず、両方選択したとき中心を優先する
              ls_guidemenu
              (list
               (list(list 76);; 地表面標高
                    (cons "ITEM"(list 22320 34920 38754 27161 39640))
                    (cons "STATUS"
                          (lambda()
                            (if str_lasground
                                (mix_strasc
                                 (list "{\\C" str_gcol_c ";" 12487 12540 12479 "} : "
                                       (vl-string-subst "" "lasgrid-" str_lasground)))
                              (if height_ground
                                  (mix_strasc
                                   (list"{\\C" str_gcol_g ";" 27161 39640 "} : "
                                        (as-numstr height_ground)))
                                (mix_strasc
                                 (list "{\\C" str_gcol_r ";"
                                       36984 25246 12373 12428 12390 12356 12414 12379 12435 "}"))
                                ))
                            ))
                    (cons "LOADFUNCTION"(lambda()(settile_selectground)))
                    (cons "HELP"(lambda()(mix_strasc(list 20351 29992 12377 12427 27161 39640 12434 "\n- las" 35501 36796 "\n- xml" 35501 36796 "\n- " 19968 23450 27161 39640 12398 25968 20516 20837 21147 "\n" 12363 12425 36984 25246 12391 12365 12414 12377 ))))
                    )

               (list(list 67);;特殊部の色
                    (cons "ITEM"(list 29305 27530 37096 12398 33394))
                    (cons "INPUTCOLOR"(lambda()
                                        (if int_colccbox_temp T(setq int_colccbox_temp int_colccbox))
                                        'int_colccbox_temp))
                    (cons "LOADFUNCTION"
                          (lambda()
                            nil
                            ))
                    ;;カラーダイアログが表示され、特殊部のモデルに使う色を選択できます
                    (cons "HELP"(lambda()(mix_strasc(list 12459 12521 12540 12480 12452 12450 12525 12464 12364 34920 31034 12373 12428 12289 29305 27530 37096 12398 12514 12487 12523 12395 20351 12358 33394 12434 36984 25246 12391 12365 12414 12377 ))))
                    )
               
               
               (list(list 69);;E特殊部天端から地表面まで
                    (cons "ITEM"(list 29305 27530 37096 22825 31471 12363 12425 22320 34920 38754 12414 12391))
                    (cons "INPUT"(lambda()
                                   (if height_ccboxtop_temp T
                                     (setq height_ccboxtop_temp height_ccboxtop))
                                   'height_ccboxtop_temp))
                    (cons "LOADFUNCTION"
                          (lambda()nil))
                    ;;特殊部の天端から地表面までの高さで、マンホールを作成するときマンホール高さを表す数値となります
                    (cons "HELP"(lambda()(mix_strasc(list 29305 27530 37096 12398 22825 31471 12363 12425 22320 34920 38754 12414 12391 12398 39640 12373 12391 12289 12510 12531 12507 12540 12523 12434 20316 25104 12377 12427 12392 12365 12510 12531 12507 12540 12523 39640 12373 12434 34920 12377 25968 20516 12392 12394 12426 12414 12377 (if int_selectmenu str_guide_inputval str_guide_selectval)))))
                    )
               (list(list 72);;H特殊部高さ
                    (cons "ITEM"(list 29305 27530 37096 39640 12373))
                    (cons "INPUT"(lambda()
                                   (if height_ccbox_temp T
                                     (setq height_ccbox_temp height_ccbox))
                                   'height_ccbox_temp))
                    (cons "LOADFUNCTION"
                          (lambda()nil))
                    ;;
                    (cons "HELP"(lambda()(mix_strasc(list(if int_selectmenu str_guide_inputval str_guide_selectval)))))
                    )
               
               
               (list(list 87);;W均しコンオフセット
                    (cons "ITEM"(list 22343 12375 12467 12531 12458 12501 12475 12483 12488))
                    (cons "INPUT"(lambda()
                                   (if offset_levelingcon_temp T
                                     (setq offset_levelingcon_temp offset_levelingcon))
                                   'offset_levelingcon_temp))
                    ;;特殊部の全周に入力値を加える
                    (cons "HELP"(lambda()(mix_strasc(list 29305 27530 37096 12398 20840 21608 12395 20837 21147 20516 12434 21152 12360 12427(if int_selectmenu str_guide_inputval str_guide_selectval)))))
                    )
               (list(list 84);;T均しコン高さ
                    (cons "ITEM"(list 22343 12375 12467 12531 39640 12373))
                    (cons "INPUT"(lambda()
                                   (if height_levelingcon_temp T
                                     (setq height_levelingcon_temp height_levelingcon))
                                   'height_levelingcon_temp))
                    (cons "HELP"(lambda()(mix_strasc(list(if int_selectmenu str_guide_inputval str_guide_selectval)))))
                    )
               
               (list(list 49);;特殊部起点を選択
                    (cons "ITEM"(list 29305 27530 37096 32 36215 28857 12434 36984 25246 ))
                    (cons "GETPOINT"(lambda()(list p_ccbox0(itoa str_colccbox0))))
                    (cons "LOADFUNCTION"
                          (lambda(bool)
                            (setq int_selectmenu nil)
                            (if(/= int_ccboxmode 0)
                                (x-alert(list 20316 25104 12514 12540 12489 12398 12392 12365 23455 34892 21487 33021 ))
                              (progn
                                (if bool(setq p_ccbox0 elem_grread))
                                (setq bool_replacegrread T int_grread 2 elem_grread 50)
                                ))
                            ))
                    ;;特殊部の点を3つ選択します
                    ;;1点目と2点目で特殊部のいずれかの辺を表し、3点目はその辺と平行な辺上の任意の点を表します
                    ;;1点目
                    (cons "HELP"(lambda()(mix_strasc(list 29305 27530 37096 12398 28857 12434 "3" 12388 36984 25246 12375 12414 12377 "\n1" 28857 30446 12392 "2" 28857 30446 12391 29305 27530 37096 12398 12356 12378 12428 12363 12398 36794 12434 34920 12375 12289 "3" 28857 30446 12399 12381 12398 36794 12392 24179 34892 12394 36794 19978 12398 20219 24847 12398 28857 12434 34920 12375 12414 12377 "\n1" 28857 30446 (if int_selectmenu str_guide_point)))))
                    )
               
               (list(list 50);;特殊部辺の端点を選択
                    (cons "ITEM"(list 29305 27530 37096 32 36794 12398 31471 28857 12434 36984 25246  ))
                    (cons "GETPOINT"(lambda()(list p_ccbox1(itoa str_colccbox1))))
                    (cons "LOADFUNCTION"
                          (lambda(bool)
                            (setq int_selectmenu nil)
                            (if(/= int_ccboxmode 0)
                                (x-alert(list 20316 25104 12514 12540 12489 12398 12392 12365 23455 34892 21487 33021 ))
                              (progn
                                (if bool(setq p_ccbox1 elem_grread))
                                (setq bool_replacegrread T int_grread 2 elem_grread 51)
                                ))
                            ))
                    (cons "HELP"(lambda()(mix_strasc(list 29305 27530 37096 12398 28857 12434 "3" 12388 36984 25246 12375 12414 12377 "\n1" 28857 30446 12392 "2" 28857 30446 12391 29305 27530 37096 12398 12356 12378 12428 12363 12398 36794 12434 34920 12375 12289 "3" 28857 30446 12399 12381 12398 36794 12392 24179 34892 12394 36794 19978 12398 20219 24847 12398 28857 12434 34920 12375 12414 12377 "\n2" 28857 30446 (if int_selectmenu str_guide_point)))))
                    )
               
               (list(list 51);;特殊部対辺上の点を選択
                    (cons "ITEM"(list 29305 27530 37096 32 23550 36794 19978 12398 28857 12434 36984 25246) )
                    (cons "GETPOINT"(lambda()(list p_ccbox2(itoa str_colccbox2))) )
                    (cons "LOADFUNCTION"
                          (lambda(bool)
                            (setq int_selectmenu nil)
                            (if(/= int_ccboxmode 0)
                                (x-alert(list 20316 25104 12514 12540 12489 12398 12392 12365 23455 34892 21487 33021 ))
                              (progn
                                (if bool(setq p_ccbox2 elem_grread))
                                (setq bool_replacegrread T int_grread 2 elem_grread 52)
                                ))
                            ))
                    (cons "HELP"(lambda()(mix_strasc(list 29305 27530 37096 12398 28857 12434 "3" 12388 36984 25246 12375 12414 12377 "\n1" 28857 30446 12392 "2" 28857 30446 12391 29305 27530 37096 12398 12356 12378 12428 12363 12398 36794 12434 34920 12375 12289 "3" 28857 30446 12399 12381 12398 36794 12392 24179 34892 12394 36794 19978 12398 20219 24847 12398 28857 12434 34920 12375 12414 12377 "\n3" 28857 30446 (if int_selectmenu str_guide_point)))))
                    
                    )
               
               
               (list(list 52);;マンホール-円周上の点1を選択
                    (cons "ITEM"(list 12510 12531 12507 12540 12523 32 20870 21608 19978 12398 28857 "1" 12434 36984 25246 ))
                    (cons "GETPOINT" (lambda()(list p_manhole_edge(itoa str_colmanhole_edge))))
                    (cons "GETPOINTSNAP" ",_nea")
                    (cons "LOADFUNCTION"
                          (lambda(bool)
                            (setq int_selectmenu nil)
                            (if(/= int_ccboxmode 0)
                                (x-alert(list 20316 25104 12514 12540 12489 12398 12392 12365 23455 34892 21487 33021 ))
                              (progn
                                (setq str_addsnap "")
                                (if bool(setq p_manhole_edge elem_grread))
                                (setq bool_replacegrread T int_grread 2 elem_grread 53)
                                ))
                            ))

                    ;;マンホールは円周上の点を3つクリックすることで中心と直径を自動計算して作成されます
                    (cons "HELP"(lambda()(mix_strasc(list 12510 12531 12507 12540 12523 12399 20870 21608 19978 12398 28857 12434 "3" 12388 12463 12522 12483 12463 12377 12427 12371 12392 12391 20013 24515 12392 30452 24452 12434 33258 21205 35336 31639 12375 12390 20316 25104 12373 12428 12414 12377  
                                                          (if int_selectmenu str_guide_point)))))
                    
                    )
               
               (list(list 53);;マンホール-円周上の点2を選択
                    (cons "ITEM"(list 12510 12531 12507 12540 12523 32 20870 21608 19978 12398 28857 "2" 12434 36984 25246 ))
                    (cons "GETPOINT" (lambda()(list p_manhole_edge1(itoa str_colmanhole_edge))))
                    (cons "GETPOINTSNAP" ",_nea")
                    (cons "LOADFUNCTION"
                          (lambda(bool)
                            (setq int_selectmenu nil)
                            (if(/= int_ccboxmode 0)
                                (x-alert(list 20316 25104 12514 12540 12489 12398 12392 12365 23455 34892 21487 33021 ))
                              (progn
                                (setq str_addsnap "")
                                (if bool(setq p_manhole_edge1 elem_grread))
                                (setq bool_replacegrread T int_grread 2 elem_grread 54)
                                ))
                            ))

                    ;;マンホールは円周上の点を3つクリックすることで中心と直径を自動計算して作成されます
                    (cons "HELP"(lambda()(mix_strasc(list 12510 12531 12507 12540 12523 12399 20870 21608 19978 12398 28857 12434 "3" 12388 12463 12522 12483 12463 12377 12427 12371 12392 12391 20013 24515 12392 30452 24452 12434 33258 21205 35336 31639 12375 12390 20316 25104 12373 12428 12414 12377  
                                                          (if int_selectmenu str_guide_point)))))
                    )

               
               (list(list 54);;マンホール-円周上の点2を選択
                    (cons "ITEM"(list 12510 12531 12507 12540 12523 32 20870 21608 19978 12398 28857 "3" 12434 36984 25246 ))
                    (cons "GETPOINT" (lambda()(list p_manhole_edge2(itoa str_colmanhole_edge))))
                    (cons "GETPOINTSNAP" ",_nea")
                    (cons "LOADFUNCTION"
                          (lambda(bool)
                            (setq int_selectmenu nil)
                            (if(/= int_ccboxmode 0)
                                (x-alert(list 20316 25104 12514 12540 12489 12398 12392 12365 23455 34892 21487 33021 ))
                              (progn
                                (setq str_addsnap "")
                                (if bool(setq p_manhole_edge2 elem_grread))
                                (setq bool_replacegrread T int_grread 2 elem_grread 55)
                                ))
                            ))

                    ;;マンホールは円周上の点を3つクリックすることで中心と直径を自動計算して作成されます
                    (cons "HELP"(lambda()(mix_strasc(list 12510 12531 12507 12540 12523 12399 20870 21608 19978 12398 28857 12434 "3" 12388 12463 12522 12483 12463 12377 12427 12371 12392 12391 20013 24515 12392 30452 24452 12434 33258 21205 35336 31639 12375 12390 20316 25104 12373 12428 12414 12377  
                                                          (if int_selectmenu str_guide_point)))))
                    
                    )

               (list(list 88);;マンホール-中心を選択
                    (cons "ITEM"(list 12510 12531 12507 12540 12523 32 20013 24515 12434 36984 25246 ))
                    (cons "GETPOINT" (lambda() (list p_manhole(itoa str_colmanhole))))
                    (cons "GETPOINTSNAP" ",_cen")
                    (cons "LOADFUNCTION"
                          (lambda(bool)
                            (setq int_selectmenu nil)
                            (if(/= int_ccboxmode 0)
                                (x-alert(list 20316 25104 12514 12540 12489 12398 12392 12365 23455 34892 21487 33021 ))
                              (progn
                                (setq str_addsnap "")
                                (if bool(setq p_manhole elem_grread))
                                ))
                            ))
                    ;;マンホールの中心
                    (cons "HELP"(lambda()(mix_strasc(list 12510 12531 12507 12540 12523 12398 20013 24515 (if int_selectmenu str_guide_point)))))
                    )
               (list(list 68);;Dマンホール直径
                    (cons "ITEM"(list 12510 12531 12507 12540 12523 30452 24452))
                    (cons "INPUT"(lambda()
                                   (if diam_manhole_temp T
                                     (setq diam_manhole_temp diam_manhole))
                                   'diam_manhole_temp))
                    (cons "HELP"(lambda()(mix_strasc(list(if int_selectmenu str_guide_inputval str_guide_selectval)))))
                    )

               

               (list(list 78);;特殊部の名称
                    (cons "ITEM"(list 29305 27530 37096 12398 21517 31216))
                    (cons "INPUTSTR"
                          (lambda( / str i bool func)
                            (if(= str_ccboxname "")(setq str_ccboxname nil))
                            (if(if str_ccboxname
                                   (if(= int_allow_overwrite 1) nil
                                     (null
                                      (vl-catch-all-error-p
                                       (vl-catch-all-apply 'vla-Item(list vnam_blocktable str_ccboxname))))
                                     )
                                 T)
                                (progn
                                  (setq str "CCBOX$" i 0 bool T)
                                  (while bool
                                    (setq i(1+ i)
                                          str_ccboxname(strcat str(substr(itoa(+ 1000 i))2))
                                          bool
                                          (null
                                           (vl-catch-all-error-p
                                            (vl-catch-all-apply 'vla-Item(list vnam_blocktable str_ccboxname))))
                                          )
                                    )
                                  ))
                            'str_ccboxname)
                          )
                    (cons "NO-INPUT" (lambda()nil ))
                    (cons "LOADFUNCTION"
                          (lambda(str / bool)
                            (setq bool
                                  (vl-catch-all-error-p
                                   (vl-catch-all-apply 'vla-Item(list vnam_blocktable str)))
                                  )
                            (if bool T
                              (if(= int_allow_overwrite 0)nil
                                (progn
                                  (alert
                                   (mix_strasc(list 26082 12395 23384 22312 12377 12427 12502 12525 12483 12463 21517 31216 12391 12377 12364 19978 26360 12365 12373 12428 12414 12377 ))
                                   )
                                  T)))
                            )
                          )
                    (cons "STRINPUTALERT"
                          (mix_strasc(list 12502 12525 12483 12463 21517 31216 12364 26082 12395 23384 22312 12375 12390 12356 12414 12377 )))
                    
                    ;;これから作成する特殊部、編集中の特殊部管路の名称を変更します\n特殊部はブロックとして作成されすでに使用されているブロック名称は設定できません
                    ;;\n名前を付けないとき「CCBOX$(使用されていない数値)」を自動的に設定します
                    (cons "HELP"(lambda()(mix_strasc(list 12371 12428 12363 12425 20316 25104 12377 12427 29305 27530 37096 12289 32232 38598 20013 12398 29305 27530 37096 31649 36335 12398 21517 31216 12434 22793 26356 12375 12414 12377 "\n" 29305 27530 37096 12399 12502 12525 12483 12463 12392 12375 12390 20316 25104 12373 12428 12377 12391 12395 20351 29992 12373 12428 12390 12356 12427 12502 12525 12483 12463 21517 31216 12399 35373 23450 12391 12365 12414 12379 12435 "\n" 21517 21069 12434 20184 12369 12394 12356 12392 12365 12300 "CCBOX$(" 20351 29992 12373 12428 12390 12356 12394 12356 25968 20516 ")" 12301 12434 33258 21205 30340 12395 35373 23450 12375 12414 12377))))
                    
                    )
               
               (list(list 77)
                    (cons "ITEM"(list 12514 12540 12489 20999 26367 ))
                    (cons "INPUTSWITCH"
                          (lambda()
                            (list 'int_ccboxmode
                                  (mapcar 'mix_strasc;;作成名称変更削除
                                          (list(list "{\\C" str_gcol_y ";" 20316 25104 "}")
                                               (list "{\\C" str_gcol_g ";" 21517 31216 22793 26356 "}")
                                               (list "{\\C" str_gcol_p ";" 21066 38500 "}")
                                               )))
                            ))
                    (cons "LOADFUNCTION"
                          (lambda()
                            
                            (cond
                             ((= int_ccboxmode 0)
                              
                              (setq bool_point T
                                    bool_selectent nil bool_select nil int_selectmode -1
                                    ls_ssget nil xtype_ssget nil xdata_ssget nil
                                    p_ccbox0 nil p_ccbox1 nil p_ccbox2 nil
                                    p_manhole nil p_manhole_edge nil p_manhole_edge1 nil p_manhole_edge2 nil
                                    )
                              
                              )
                             ((= int_ccboxmode 1)
                              (setq bool_point nil
                                    bool_selectent nil bool_select nil int_selectmode -1
                                    ls_vnam_selevt(list)
                                    ls_ssget(list(cons 0 "INSERT"))
                                    xtype_ssget "CCBOXBLOCK" xdata_ssget "terraduct3d"
                                    p_ccbox0 nil p_ccbox1 nil p_ccbox2 nil
                                    p_manhole nil  p_manhole_edge nil  p_manhole_edge1 nil p_manhole_edge2 nil
                                    )
                              )
                             ((= int_ccboxmode 2)
                              (setq bool_point nil
                                    bool_selectent T bool_select T int_selectmode 0
                                    ls_vnam_selevt(list)
                                    ls_ssget(list(cons 0 "INSERT"))
                                    xtype_ssget "CCBOXBLOCK" xdata_ssget "terraduct3d"
                                    p_ccbox0 nil p_ccbox1 nil p_ccbox2 nil
                                    p_manhole nil p_manhole_edge nil p_manhole_edge1 nil p_manhole_edge2 nil
                                    )
                              )
                             )
                            
                            ))
                    
                    ;;-作成：平面図の点を選択して特殊部作成
                    ;;\n-名称変更：作成済みの特殊部を選択して名称を編集する
                    ;;\n-削除：特殊部を選択して削除
                    (cons "HELP"
                          (lambda()
                            (mix_strasc(list "-" 20316 25104 65306 24179 38754 22259 12398 28857 12434 36984 25246 12375 12390 29305 27530 37096 20316 25104 "\n-" 21517 31216 22793 26356 65306 20316 25104 28168 12415 12398 29305 27530 37096 12434 36984 25246 12375 12390 21517 31216 12434 32232 38598 12377 12427 "\n-" 21066 38500 65306 29305 27530 37096 12434 36984 25246 12375 12390 21066 38500 ))))
                    
                    )
               
               (list(list 80 );;P選択モード切替
                    (cons "ITEM"(list 36984 25246 12514 12540 12489 20999 26367 ))
                    (cons "INPUTSWITCH"
                          (lambda()
                            (setq int_temp 0)
                            (if(= int_ccboxmode 2)
                                (if(= int_selectmode -1)
                                    (list nil(mix_strasc
                                              (list "{\\C" str_gcol_p ";"
                                                    21336 20307 36984 25246 12398 12415 "}")))
                                  (list 'int_selectmode
                                        (mapcar 'mix_strasc
                                                (list(list "{\\C" str_gcol_y ";" 36984 25246 "}")
                                                     (list "{\\C" str_gcol_c ";" 35299 38500 "}")))
                                        ))
                              (list 'int_temp ;;削除モードのとき使用可能
                                    (list(mix_strasc
                                          (list "{\\C" str_gcol_p ";"
                                                21066 38500 12514 12540 12489 12398 12392 12365 20351 29992 21487 33021 "}")))
                                    )
                              )) )
                    (cons "HELP"(lambda()str_guide_selectmode))
                    )
               
               
               (list(list nil)
                    (cons "ITEM"(list ))
                    (cons "BOOL"
                          (lambda()
                            T
                            ))
                    (cons
                     "STATUS"
                     (lambda( / bool_depth ii ls_out)
                       (setq ls_out
                             (cond
                              ((= int_ccboxmode 0);;作成編集
                               (if(and p_ccbox0 p_ccbox1 p_ccbox2)
                                   (list
                                    (list
                                     "{\\C" str_gcol_y ";";;特殊部作成
                                     " - Enter : " 29305 27530 37096 20316 25104 "}"
                                     "{\\C" str_gcol_g ";";;マンホールありなし
                                     "  " 12510 12531 12507 12540 12523
                                     (if(or p_manhole(and p_manhole_edge p_manhole_edge1 p_manhole_edge2))
                                         (list 12354 12426)(list 12394 12375 )) "}"
                                         )
                                    )
                                 (list
                                  (list
                                   "{\\C" str_gcol_p ";" ;;点の選択が足りません
                                    28857 12398 36984 25246 12364 36275 12426 12414 12379 12435 "}"
                                    )
                                  )
                                 )
                               )
                              
                              ((= int_ccboxmode 1);;名称変更
                               (list
                                (list
                                 "{\\C" str_gcol_g ";";;特殊部作成
                                 " - " 20316 25104 28168 12415 12398 29305 27530 37096 12434 36984 25246 12377 12427 12392 29694 22312 35373 23450 12373 12428 12390 12356 12427 21517 31216 12434 36969 29992 12373 12379 12414 12377 )
                                ;;作成済みの特殊部を選択すると現在設定されている名称を適用させます
                                (list
                                 " - " 26032 12383 12395 35373 23450 12373 12428 12383 21517 31216 12364 12377 12391 12395 22259 38754 20869 12391 20351 12431 12428 12390 12356 12427 12392 12365 12289 )
                                
                                ;;新たに設定された名称がすでに図面内で使われているとき、
                                (list
                                 "   " 12381 12398 12458 12502 12472 12455 12463 12488 12399 21066 38500 12373 12428 12414 12377 )
                                ;;そのオブジェクトは削除されます
                                )
                               
                               )
                              ((= int_ccboxmode 2) ;;削除
                               (list
                                (list
                                 "{\\C" str_gcol_p ";"
                                 " - " 29305 27530 37096 12434 36984 25246 12375 12390 "Enter : "
                                 21066 38500 "}"
                                 ;;特殊部を選択してEnter:削除
                                 )
                                )
                               )
                              );;cond
                             ls_out(vl-remove nil ls_out)
                             )
                       ls_out
                       ))
                    )
               
               (list(list "ENTER");;メインメニューへ
                    (cons "ITEM"(list 12513 12452 12531 12513 12491 12517 12540 12408))
                    (cons "LOADFUNCTION"
                          (lambda()
                            (setq str_next
                                  (if(or p_ccbox0 p_ccbox1 p_ccbox2 p_manhole)
                                      nil "home"))
                            ))
                    (cons "NEXTMODE" "home")
                    )

               )

              bool_replacegrread T int_grread 2 elem_grread 49
              
              
              )
             
             ))
       
       (if(cadr bool) (list ) )
       ))
    
    (cons
     "MOVE"
     (lambda();;gr5

       (mapcar
        '(lambda(p c / s ls_p)
           (if p
               (progn
                 (setq s(* height_text 0.8)
                       ls_p(mapcar
                            '(lambda(xx yy)
                               (mapcar '(lambda(a x y)(+ a(* xx x)(* yy y)))
                                       p vec_x_onview vec_y_onview)
                               )
                            (list s(- s)(- s)s) (list s(- s)s(- s)))
                       )
                 (mapcar '(lambda(p0 p1)(grdraw p0 p1 c))
                         (list(car ls_p)(caddr ls_p))
                         (list(cadr ls_p)(cadddr ls_p)))
                 ))
           )
        (list p_ccbox0 p_ccbox1 p_ccbox2 p_manhole p_manhole_edge p_manhole_edge1 p_manhole_edge2)
        (list str_colccbox0 str_colccbox1 str_colccbox2 str_colmanhole str_colmanhole_edge str_colmanhole_edge str_colmanhole_edge)
        )
       
       ))
    
    (cons
     "CLICK"
     (lambda( / )
       (cond
        ((if(if(= int_ccboxmode 1)
                (if(setq set_ent(ssget elem_grread(list(cons 0 "INSERT")(list -3(list "terraduct3d")))))
                    (setq vnam(vlax-ename->vla-object(ssname set_ent 0)))))
             (progn
               (vla-getXData vnam "terraduct3d" 'array_Type 'array_Data )
               (setq ls_xdata
                     (if array_data
                         (split_list 0(mapcar 'vlax-variant-value
                                              (vlax-safearray->list array_data))))
                     )
               
               (=(cdr(assoc "terraduct3d" ls_xdata))"CCBOXBLOCK")
               ))
         
         (setq str_bname(vla-get-name vnam)
               block(vl-catch-all-apply 'vla-Item(list vnam_blocktable str_bname)))
         

         (settile_strinput;;名称変更
          'str_bname
          (lambda(a)
            (if(= a str_bname)T
              (vl-catch-all-error-p
               (vl-catch-all-apply 'vla-Item(list vnam_blocktable a))))
            )
          
          (mix_strasc(list 21517 31216 22793 26356 ))
          (mix_strasc(list 26082 12395 23384 22312 12377 12427 21517 31216 12399 20351 12360 12414 12379 12435 ))
          ;;既に存在する名称は使えません
          )
         
         (if(if str_bname(/= str_bname ""))(vla-put-name block str_bname))

         
         (mapcar '(lambda(v)
                    (vlax-release-object v)
                    (setq ls_vla-release(vl-remove v ls_vla-release))
                    )
                 (list block))
         )
        )
       )
     )
    
    ;;  (lambda()nil ))

    (cons
     "KEYBOAD"
     (lambda( / ls_p)
       (cond
        ((and(or(= elem_grread 13)(= int_grread 25))
             (= int_ccboxmode 2))
         
         (mapcar
          '(lambda(vnam)
             (if(vlax-erased-p vnam)T
               (progn
                 (setq str(vla-get-name vnam))
                 (if(setq set_ent(ssget "X"(list(cons 2 str))))
                     (progn
                       (setq num(sslength set_ent))
                       (while(>(setq num(1- num))-1)
                         (setq vnam(vlax-ename->vla-object(ssname set_ent num))
                               ls_vnam_highlight(vl-remove vnam ls_vnam_highlight))
                         
                         (vla-delete vnam)
                         )
                       ))
                 (vla-delete
                  (vla-Item(vla-get-Blocks(vla-get-ActiveDocument
                                           (vlax-get-acad-object)))
                           str) )

                 ))
             )
          ls_vnam_select)
         
         )
        ((and(or(= elem_grread 13)(= int_grread 25))
             p_ccbox0 p_ccbox1 p_ccbox2
             (or str_lasground height_ground))

         (setq vecx(unit_vector(carxyz(mapcar '- p_ccbox1 p_ccbox0)0))
               vecy(list(-(cadr vecx))(car vecx))
               width_ccbox(apply '+(mapcar '*(mapcar '- p_ccbox2 p_ccbox0)vecy))
               )

         ((lambda(p0 p1 p2 / px00 px01 px10 px11 vec)
            (if p_manhole T
              (if(if(and p0 p1 p2)
                     (progn
                       (setq p0(carxy p0)p1(carxy p1)p2(carxy p2))
                       (and(>(distance p0 p1)1e-5)(>(distance p1 p2)1e-5)(>(distance p2 p0)1e-5))
                       ))
                  (setq px00(mapcar '(lambda(a b)(* 0.5(+ a b)))p1 p2)
                        px01(mapcar '+ px00(list(-(cadr p1)(cadr p2))(-(car p2)(car p1))))
                        px10(mapcar '(lambda(a b)(* 0.5(+ a b)))p0 p2)
                        px11(mapcar '+ px10(list(-(cadr p0)(cadr p2))(-(car p2)(car p0))))
                        p_manhole(inters px00 px01 px10 px11 nil)
                        diam_manhole_temp(* 2(distance p_manhole p0))
                        diam_manhole_temp(atof(rtos diam_manhole_temp 2 3))
                        p_manhole(carxyz p_manhole 0) )
                (setq p_manhole nil diam_manhole_temp 0.))))
          p_manhole_edge p_manhole_edge1 p_manhole_edge2)
         
         (cond
          ((<(abs width_ccbox)1e-8)
           (x-alert(list "3" 28857 12364 30452 32218 19978 12391 12354 12427 12383 12417 20316 25104 12391 12365 12414 12379 12435 ))
           ;;3点が直線上であるため作成できません
           )
          ((setq ls_p
                 (if p_manhole
                     (project_to_ground
                      (list p_manhole)
                      (list 0. 0. 1.)(list str_lasground height_ground))
                   (project_to_ground
                    (list p_ccbox0 p_ccbox1 p_ccbox2)
                    (list 0. 0. 1.)(list str_lasground height_ground))))

           (if(< width_ccbox 0) (setq width_ccbox(- width_ccbox) vecy(mapcar '- vecy)))
           
           (setq elevation_ground(/(apply '+(mapcar 'caddr ls_p))(length ls_p))
                 elevation_ccbox(- elevation_ground height_ccboxtop_temp height_ccbox_temp)
                 widthx05(* 0.5(apply '+(mapcar '*(mapcar '- p_ccbox1 p_ccbox0)vecx)))
                 
                 p_ccboxc(mapcar '(lambda(a x y)(+ a(* widthx05 x)(* 0.5 width_ccbox y)))
                                 p_ccbox0 vecx vecy)
                 p_ccboxc(carxyz p_ccboxc elevation_ccbox)
                 entna(rac_sld widthx05(* 0.5 width_ccbox)height_ccbox_temp
                               p_ccboxc 0(list 0 0 1)vecx(getvar "CLAYER")nil)
                 ;;(code_loft_solid lsls_point nil nil)
                 vnam(vlax-ename->vla-object entna)
                 ls_vnam(list vnam)
                 )
           (set_xda vnam(list(cons 1000 "CCBOXSOLID")
                             )
                    "terraduct3d")
           (vla-put-color vnam int_colccbox_temp)
           
           (setq vec_normal(list(-(car vecy))(-(cadr vecy))0)
                 dist_normal(apply '+(mapcar '* p_ccbox0 vec_normal))
                 )
           (mapcar
            '(lambda(lst / p0 p1 vec_normal dist_normal vecy ang hh str_xdata)
               (mapcar 'set '(p0 p1 vec_normal dist_normal vecy ang hh str_xdata)lst)
               (setq entna(make_2pdimension
                           nil(list p0 p1 vec_normal dist_normal vecy ang hh
                                    "" str_dimstyle_ductlevel))
                     vnam(vlax-ename->vla-object entna)
                     ls_vnam(cons vnam ls_vnam)
                     )
               (vla-put-Arrowhead1Type vnam 13)
               (vla-put-Arrowhead2Type vnam 6)
               
               (set_xda vnam(list(cons 1000 str_xdata) )
                        "terraduct3d")
               )
            (list(list(carxyz p_ccbox0 elevation_ccbox)(carxyz p_ccbox1 elevation_ccbox)
                      vec_normal dist_normal(list 0 0 1)0.(* 0.2 height_ccbox_temp)
                      "CCBOXWIDTH-X")
                 (list(carxyz p_ccbox0 elevation_ccbox)
                      (carxyz p_ccbox0(+ elevation_ccbox height_ccbox_temp))
                      vec_normal dist_normal(mapcar '- vecx)(* 0.5 pi)
                      (* 0.2 height_ccbox_temp)
                      "CCBOXHEIGHT")
                 (list(carxyz p_ccbox0(+ elevation_ccbox height_ccbox_temp))
                      (carxyz p_ccbox0 elevation_ground)
                      vec_normal dist_normal(mapcar '- vecx)(* 0.5 pi)
                      (* 0.2 height_ccbox_temp)
                      "CCBOXVBACANT")
                 (list(mapcar '(lambda(a b)(+ a(* -1 b width_ccbox)))
                              (carxyz p_ccbox0 elevation_ccbox)vec_normal)
                      (carxyz p_ccbox0 elevation_ccbox)
                      (mapcar '- vecx)(-(apply '+(mapcar '* vecx p_ccbox0)))
                      (list 0 0 1)0.(* 0.2 height_ccbox_temp)
                      "CCBOXWIDTH-Y")
                 )
            )
           
           (if(< height_levelingcon_temp 1e-8)T
             (progn
               (setq entna(rac_sld(+ widthx05 offset_levelingcon_temp)
                                  (+(abs(* 0.5 width_ccbox)) offset_levelingcon_temp)
                                  height_levelingcon_temp
                                  (carxyz p_ccboxc(- elevation_ccbox height_levelingcon_temp))
                                  0(list 0 0 1)vecx(getvar "CLAYER")nil)
                     vnam(vlax-ename->vla-object entna)
                     ls_vnam(cons vnam ls_vnam)
                     )
               
               (set_xda vnam(list(cons 1000 "LEVELINGCON")
                                 (cons 1000 "OFFSET")(cons 1040 offset_levelingcon_temp)
                                 (cons 1000 "HEIGHT")(cons 1040 height_levelingcon_temp)
                                 )
                        "terraduct3d")
               (vla-put-color vnam int_colccbox_temp)
               
               ))

           
           (if(and(/= height_ccboxtop_temp 0.) (/= diam_manhole_temp 0.)p_manhole)
               (progn
                 (setq entna(pole_sld(* diam_manhole_temp 0.5)
                                     height_ccboxtop_temp
                                     (carxyz p_manhole(+ elevation_ccbox height_ccbox_temp))
                                     (list 0 0 1)(getvar "CLAYER")nil)
                       vnam(vlax-ename->vla-object entna)
                       ls_vnam(cons vnam ls_vnam)
                       )
                 
                 (set_xda vnam(list(cons 1000 "MANHOLE")
                                   (cons 1000 "CENTER-X")(cons 1040(car p_manhole))
                                   (cons 1000 "CENTER-Y")(cons 1040(cadr p_manhole))
                                   (cons 1000 "DIAM")(cons 1040 diam_manhole_temp)
                                   (cons 1000 "HEIGHT")(cons 1040 height_ccboxtop_temp)
                                   )
                          "terraduct3d")
                 (vla-put-color vnam int_colccbox_temp)
                 
                 ))


           (if(vl-catch-all-error-p
               (setq block(vl-catch-all-apply 'vla-Item(list vnam_blocktable str_ccboxname))))
               (setq block(vla-Add vnam_blockTable(vlax-3d-point 0 0 0)str_ccboxname) )
             (progn
               ;; (if vnam_currentinsert
               ;;     (progn
               ;;       (vla-delete vnam_currentinsert)
               ;;       (setq ls_vnam_visible
               ;;             (vl-remove vnam_currentinsert ls_vnam_visible)
               ;;             vnam_currentinsert nil)
               ;;       ))
               (if(setq set_ent(ssget "X"(list(cons 2 str_ccboxname))))
                   (progn
                     (setq num(sslength set_ent))
                     (while(>(setq num(1- num))-1)
                       (setq vnam(vlax-ename->vla-object(ssname set_ent num)))
                       (vla-delete vnam)
                       )
                     ))
               (vla-delete block)
               (mapcar '(lambda(v)
                          (vlax-release-object v)
                          (setq ls_vla-release(vl-remove v ls_vla-release))
                          )
                       (list block))
               (setq block(vla-Add vnam_blockTable(vlax-3d-point 0 0 0)str_ccboxname))
               )
             )

           (setq ls_vla-release(cons block ls_vla-release))

           (vla-copyobjects(vla-get-ActiveDocument(vlax-get-acad-object))
                           (vlax-make-variant
                            (vlax-safearray-fill
                             (vlax-make-safearray
                              vlax-vbObject(cons 0(1-(length ls_vnam))) )
                             ls_vnam)
                            )
                           block)
           
           (setq vnam(vla-InsertBlock
                      (vla-get-ModelSpace(vla-get-ActiveDocument(vlax-get-acad-object)))
                      (vlax-3d-point 0 0 0)str_ccboxname 1 1 1 0)
                 )
             
           (set_xda vnam(list(cons 1000 "CCBOXBLOCK")
                             (cons 1000 "PROJECT-D")(cons 1000(if str_lasground str_lasground ""))
                             (cons 1000 "PROJECT-H")(cons 1040(if height_ground height_ground 0.))
                             )
                    "terraduct3d")
           
           (mapcar '(lambda(a)(vla-delete a))ls_vnam)
           
           )
          (T
           (x-alert(list 36984 25246 12375 12383 28857 12363 12425 27161 39640 12364 21462 24471 12391 12365 12414 12379 12435 ))
           ;;選択した点から標高が取得できません
           )
          )
         
         
         (setq p_ccbox0 nil p_ccbox1 nil p_ccbox2 nil p_manhole nil p_manhole_edge nil p_manhole_edge1 nil p_manhole_edge2 nil)
         )
        ((and(or(= elem_grread 13)(= int_grread 25))
             (or str_lasground height_ground))
         (x-alert(list 28857 12398 36984 25246 12364 36275 12426 12414 12379 12435 ))
         ;;点の選択が足りません
         )
        ((and(or(= elem_grread 13)(= int_grread 25)))
         (x-alert(list 22320 34920 38754 12398 36984 25246 12364 12354 12426 12414 12379 12435 ))
         ;;地表面の選択がありません
         )
        )
       
       ))
    
    
    )

   (list
    "addattribute" ;;edsym
    (cons
     "INITIAL"
     (lambda(bool)
       (if(car bool)
           (progn
             (setq bool_point nil
                   bool_selectent nil bool_select nil int_selectmode -1
                   ls_ssget nil xtype_ssget nil xdata_ssget nil
                   )
             
             (setq func_guidemenu
                   (lambda()
                     ;;本コマンドで作成したものを選択すると属性付与できます
                     ;;\n対象をクリックしてください(範囲選択はできません)
                     (mix_strasc
                      (list 26412 12467 12510 12531 12489 12391 20316 25104 12375 12383 12418 12398 12434 36984 25246 12377 12427 12392 23646 24615 20184 19982 12391 12365 12414 12377
                             "\n" 23550 35937 12434 12463 12522 12483 12463 12375 12390 12367 12384 12373 12356 "(" 31684 22258 36984 25246 12399 12391 12365 12414 12379 12435 ")")
                      ) )
                   
                   ls_guideexplane
                   (mapcar
                    'mix_strasc
                    (list(list " - "36984 25246 12375 12390 19979 12373 12356)
                         (list " - " 20184 19982 24460 12395 32232 38598 12434 34892 12358 12392 12522 12475 12483 12488 12373 12428 12414 12377 )
                         ;;付与後に編集を行うとリセットされます
                         ) )
                   
                   ls_guidemenu
                   (list
                    (list(list nil)
                         (cons "ITEM"(list ))
                         (cons "BOOL"
                               (lambda()
                                 nil
                                 ))
                         (cons "STATUS" (lambda( / bool_depth ii ls_out)
                                          nil
                                          ))
                         )
                    
                    (list(list "ENTER");;メインメニューへ
                         (cons "ITEM"(list 12513 12452 12531 12513 12491 12517 12540 12408))
                         (cons "NEXTMODE" "home")
                         )
                    
                    )
                   )
             
             ))
       (if(cadr bool) nil)
       ))
     
    ;; (cons
    ;;  "GUIDE"
    ;;  (lambda() (list "\n" 36984 25246 12375 12390 19979 12373 12356)))
    ;;選択して下さい
    
    ;;MOVE

    (cons
     "CLICK"
     (lambda()
       (axd_settile_att
        path_addattributedcl elem_grread
        (list(list -3(list "terraduct3d"))) )
       ))
    
    (cons
     "KEYBOAD"
     (lambda();;gr2
       (if(or(= elem_grread 13)(= int_grread 25))
           (setq str_edit "home"))
       ))
    
    )
   
   
   (list
    "influencecheck"
    (cons
     "INITIAL"
     (lambda(bool);;initial
       (if(car bool)
           (progn
             ;;temp
             (setq bool_point nil
                   bool_selectent T bool_select T int_selectmode 0
                   ls_ssget(list(cons 0 "INSERT"))
                   xtype_ssget "DUCTBLOCK" xdata_ssget "terraduct3d"
                   )
             
             (setq ls_vnam_tempinfluence(list)
                   int_execute_influence nil)
             (setq
              func_guidemenu
              (lambda()
                ;;対象に対して土被り、干渉、または両方を計算します
                ;;\n管路を対象に選択でき、その他のものは選択しようとしてもハイライトされません
                ;;\n何も選択しないとき、すべて選択したことになります
                ;;\n選択有り無し
                ;;\n作成されるオブジェクトは一時的なものでコマンドを終了すると削除されます
                ;;\n確定させたいときはSpaceコマンドを選択してください
                (mix_strasc
                 (list 23550 35937 12395 23550 12375 12390 22303 34987 12426 12289 24178 28169 12289 12414 12383 12399 20001 26041 12434 35336 31639 12375 12414 12377 "\n" 31649 36335 12434 23550 35937 12395 36984 25246 12391 12365 12289 12381 12398 20182 12398 12418 12398 12399 36984 25246 12375 12424 12358 12392 12375 12390 12418 12495 12452 12521 12452 12488 12373 12428 12414 12379 12435 "\n" 20309 12418 36984 25246 12375 12394 12356 12392 12365 12289 12377 12409 12390 36984 25246 12375 12383 12371 12392 12395 12394 12426 12414 12377
                       "\n" 36984 25246 12304
                       (if ls_vnam_select(list 26377 12426)(list 28961 12375)) 12305
                        "\n" 20316 25104 12373 12428 12427 12458 12502 12472 12455 12463 12488 12399 19968 26178 30340 12394 12418 12398 12391 12467 12510 12531 12489 12434 32066 20102 12377 12427 12392 21066 38500 12373 12428 12414 12377 "\n" 30906 23450 12373 12379 12383 12356 12392 12365 12399 "Space" 12467 12510 12531 12489 12434 36984 25246 12375 12390 12367 12384 12373 12356
                        
                       )
                 ) )
              
              ls_guideexplane
              (mapcar
               'mix_strasc
               (list(list " - " 31649 36335 12434 36984 25246 12375 12390 23455 34892 )
                    (list " - " 20309 12418 36984 25246 12375 12394 12356 12392 12365 12289 20316 25104 12375 12383 12377 12409 12390 12398 31649 36335 12364 23550 35937 12395 12394 12427 )
                    (list " - " 36984 25246 26178 12395 "Enter," 21491 12463 12522 12483 12463 12391 20840 36984 25246 35299 38500 )
                    ))
              ;;管路を選択して実行
              ;;何も選択しないとき、作成したすべての管路が対象になる
              ;;選択時にEnter,右クリックで全選択解除
              
              
              ls_guidemenu
              (list
               
               (list(list 76);; 地表面標高
                    (cons "ITEM"(list 22320 34920 38754 27161 39640))
                    (cons "STATUS"
                          (lambda()
                            (if str_lasground
                                (mix_strasc
                                 (list "{\\C" str_gcol_c ";" 12487 12540 12479 "} : "
                                       (vl-string-subst "" "lasgrid-" str_lasground)))
                              (if height_ground
                                  (mix_strasc
                                   (list"{\\C" str_gcol_g ";" 27161 39640 "} : "
                                        (as-numstr height_ground)))
                                (mix_strasc
                                 (list "{\\C" str_gcol_r ";"
                                       36984 25246 12373 12428 12390 12356 12414 12379 12435 "}"))
                                ))
                            ))
                    (cons "LOADFUNCTION"(lambda()(settile_selectground)))
                    (cons "HELP"(lambda()(mix_strasc(list 20351 29992 12377 12427 27161 39640 12434 "\n- las" 35501 36796 "\n- xml" 35501 36796 "\n- " 19968 23450 27161 39640 12398 25968 20516 20837 21147 "\n" 12363 12425 36984 25246 12391 12365 12414 12377 ))))
                    )
               
               (list(list 49);;土被り許容値に満たない箇所を一時表示
                    (cons "ITEM"(list 22303 34987 12426 35377 23481 20516 12395 28288 12383 12394 12356 31623 25152 12434 19968 26178 34920 31034  ))
                    (cons "NEXTMODE" str_edit);;nilでは先に進めない
                    (cons "LOADFUNCTION"
                          (lambda()
                            (setq str_next nil
                                  int_execute_influence 1)
                            ))
                    (cons "CLICKFUNCTION"
                          (lambda()(setq bool_replacegrread T int_grread 2 elem_grread 49) ))
                    
                    )

               (list(list 50);;Q土被り許容値
                    (cons "ITEM"(list 22303 34987 12426 35377 23481 20516 ))
                    (cons "INPUT"(lambda()
                                   (if allow_cover_temp T
                                     (setq allow_cover_temp allow_cover))
                                   'allow_cover_temp))

                    ;;土被りがこの値よりも小さいものが表記の対象となります
                    (cons "HELP"(lambda()(mix_strasc(list 22303 34987 12426 12364 12371 12398 20516 12424 12426 12418 23567 12373 12356 12418 12398 12364 34920 35352 12398 23550 35937 12392 12394 12426 12414 12377 (if int_selectmenu str_guide_inputval str_guide_selectval) ))))
                    
                    )
               
               ;; (list(list 65);;A土被り表示ピッチ
               ;;      (cons "ITEM"(list 22303 34987 12426 34920 31034 12500 12483 12481 ))
               ;;      (cons "INPUT"(lambda()
               ;;                     (if pitch_cover_temp T
               ;;                       (setq pitch_cover_temp pitch_cover))
               ;;                     'pitch_cover_temp))
               ;;      )

               (list(list 51);;Z土被りNG色
                    (cons "ITEM"(list 22303 34987 12426 "NG" 33394 ))
                    (cons "INPUTCOLOR"(lambda()
                                        (if int_colcoverng_temp T(setq int_colcoverng_temp int_colcoverng))
                                        'int_colcoverng_temp))
                    (cons "LOADFUNCTION"
                          (lambda()
                            nil
                            ))
                    )
               
               (list(list 81);;Q干渉許容値に満たない箇所を一時表示
                    (cons "ITEM"(list 24178 28169 35377 23481 20516 12395 28288 12383 12394 12356 31623 25152 12434 19968 26178 34920 31034 ))
                    (cons "NEXTMODE" str_edit);;nilでは先に進めない
                    (cons "LOADFUNCTION"
                          (lambda()
                            (setq str_next nil
                                  int_execute_influence 2)
                            ))
                    (cons "CLICKFUNCTION"
                          (lambda()(setq bool_replacegrread T int_grread 2 elem_grread 81) ))
                    
                    )
               
               (list(list 87);;W干渉許容値
                    (cons "ITEM"(list 24178 28169 35377 23481 20516 ))
                    (cons "INPUT"(lambda()
                                   (if allow_influence_temp T
                                     (setq allow_influence_temp allow_influence))
                                   'allow_influence_temp))
                    ;;2つの管の表面から表面までの最短距離がこの値よりも小さいとき表示します\nわずかな干渉を許すときは負の値を入力してください
                    (cons "HELP"(lambda()(mix_strasc(list "2" 12388 12398 31649 12398 34920 38754 12363 12425 34920 38754 12414 12391 12398 26368 30701 36317 38626 12364 12371 12398 20516 12424 12426 12418 23567 12373 12356 12392 12365 34920 31034 12375 12414 12377 "\n" 12431 12378 12363 12394 24178 28169 12434 35377 12377 12392 12365 12399 36000 12398 20516 12434 20837 21147 12375 12390 12367 12384 12373 12356 (if int_selectmenu str_guide_inputval str_guide_selectval) ))))
                    )
               
               (list(list 69);;E干渉NG色
                    (cons "ITEM"(list 24178 28169 "NG" 33394  ))
                    (cons "INPUTCOLOR"
                          (lambda()(if int_colinfluence_temp T(setq int_colinfluence_temp int_colinfluence))
                            'int_colinfluence_temp))
                    (cons "LOADFUNCTION"
                          (lambda()
                            nil
                            ))
                    )

               (list(list 65);;A土被りと干渉どちらも表示
                    (cons "ITEM"(list 22303 34987 12426 12392 24178 28169 12393 12385 12425 12418 34920 31034 ))
                    (cons "NEXTMODE" str_edit);;nilでは先に進めない
                    (cons "LOADFUNCTION"
                          (lambda()
                            (setq str_next nil
                                  int_execute_influence 3)
                            ))
                    (cons "CLICKFUNCTION"
                          (lambda()(setq bool_replacegrread T int_grread 2 elem_grread 65) ))
                    )


               
               (list(list 32);;一時表示オブジェクトを残す
                    (list "ITEM"(list 19968 26178 34920 31034 12458 12502 12472 12455 12463 12488 12434 27531 12377 ))
                    (cons "NEXTMODE" str_edit)
                    (cons "LOADFUNCTION"
                          (lambda()
                            (if ls_vnam_tempinfluence
                                (progn
                                  (mapcar '(lambda(vnam)(exckillobj vnam) )
                                          ls_vnam_tempinfluence)
                                  (setq str_next nil
                                        int_execute_influence 32
                                        ls_vnam_tempinfluence nil)
                                  )
                              (progn
                                (x-alert(list 23550 35937 12364 12354 12426 12414 12379 12435 ))
                                nil)
                              )
                            ))
                    ;;
                    
                    )
               
               (list(list 8);;一時オブジェクトを消す
                    (cons "ITEM"(list  19968 26178 12458 12502 12472 12455 12463 12488 12434 28040 12377 ))
                    (cons "LOADFUNCTION"
                          (lambda()
                            (mapcar '(lambda(vnam)
                                       (vla-delete vnam)
                                       (exckillobj vnam) )
                                    ls_vnam_tempinfluence)
                            (setq ls_vnam_tempinfluence nil)
                            ))
                    )
               
               (list(list 80 );;P選択モード切替
                    (cons "ITEM"(list 36984 25246 12514 12540 12489 20999 26367 ))
                    (cons "INPUTSWITCH"
                          (lambda()
                            (if(= int_selectmode -1)
                                (list nil(mix_strasc
                                          (list "{\\C" str_gcol_p ";"
                                                21336 20307 36984 25246 12398 12415 "}")))
                              (list 'int_selectmode
                                    (mapcar 'mix_strasc
                                            (list(list "{\\C" str_gcol_y ";" 36984 25246 "}")
                                                 (list "{\\C" str_gcol_c ";" 35299 38500 "}")))
                                    ))
                            ) )
                    (cons "HELP"(lambda()str_guide_selectmode))
                    )
               
               (list(list nil)
                    (cons "ITEM"(list ))
                    (cons "BOOL"
                          (lambda()
                            T
                            ))
                    (cons
                     "STATUS"
                     (lambda( / bool_depth ii ls_out)
                       (if ls_vnam_select
                           (list(list(mix_strasc(list "{\\C" str_gcol_y ";"
                                                      9733 "  " 36984 25246 20013 "}")))))
                       ))
                    )
               
               (list(list "ENTER");;メインメニューへ
                    (cons "ITEM"(list 12513 12452 12531 12513 12491 12517 12540 12408))
                    (cons "LOADFUNCTION"
                          (lambda()
                            (mapcar '(lambda(vnam)
                                       (vla-delete vnam)
                                       (exckillobj vnam) )
                                    ls_vnam_tempinfluence)
                            (setq ls_vnam_tempinfluence nil)
                            ))
                    (cons "NEXTMODE" "home")
                    )
               
               )
              
              )
             
             ))
       
       (if(cadr bool) (list ) )
       ))

    ;;MOVE
    ;;CLICK

    (cons
     "KEYBOAD"
     (lambda( / bool_default ls_solidinfluence vec_normal dist_normal)

       (cond
        ((or(= elem_grread 13)(= int_grread 25))
         (mapcar '(lambda(v)(vla-Highlight v :vlax-false))ls_vnam_select)
         (setq ls_vnam_select nil ls_vnam_highlight nil)
         )
        ((vl-position int_execute_influence(list 1 2 3))
         (setq vec_normal(unit_vector(carxyz vec_view 0.)))
         
         (if ls_vnam_select T
           ((lambda( / num ls_out vnam)
              (setq set_ent(ssget "X"(list(cons 0 "INSERT")(list -3(list "terraduct3d"))))
                    num(if set_ent(sslength set_ent)0) )
              (while(>(setq num(1- num))-1)
                (setq vnam(vlax-ename->vla-object(ssname set_ent num))
                      ls_vnam_select(cons vnam ls_vnam_select))
                )
              ))
           )
         
         (mapcar
          '(lambda(vnam / length_road str d nn vnam_line vnam_solid rr ls_p )
             (setq str(vla-get-name vnam)
                   vnam(vla-Item(vla-get-Blocks (vla-get-ActiveDocument(vlax-get-acad-object)))str)
                   )
             
             (vlax-for
              obj vnam
              
              (if(and vnam_solid vnam_line) T
                (progn
                  
                  (vla-getXData obj "terraduct3d" 'array_Type 'array_Data )
                  (setq ls_xdata
                        (if array_data
                            (split_list 0(mapcar 'vlax-variant-value
                                                 (vlax-safearray->list array_data))))
                        str_type(cdr(assoc "terraduct3d" ls_xdata))
                        )

                  (cond
                   ((= str_type "DUCTSOLID")
                    (setq rr(* 0.5(cdr(assoc "DIAM" ls_xdata))))
                    )
                   ((= str_type "CENTERLINE")
                    (setq vnam_line obj)
                    )
                   )
                  ))
              )

             (if(and vnam_line rr)
                 (progn
                   (setq length_road(vla-get-length vnam_line)
                         nn(1+(fix(/ length_road rr)))
                         d(/ length_road nn)
                         ls_p(list(vlax-curve-getendpoint vnam_line))
                         )
                   (while(< 1e-8(setq length_road(- length_road d)))
                     (setq ls_p(cons(vlax-curve-getpointatdist vnam_line length_road)ls_p))
                     )
                   (setq ls_p(reverse(cons(vlax-curve-getstartpoint vnam_line)ls_p)))
                   )
               
               )
             
             (if(and(vl-position int_execute_influence(list 1 3))rr)
                 (mapcar
                  '(lambda(p / vec pp d cosz )
                     (setq pp(car(project_to_ground
                                  (list p)(list 0. 0. 1.)(list str_lasground height_ground)))
                           d(distance p pp)
                           vec(xvla-normal vnam_line p)
                           cosz(sqrt(- 1.(expt(caddr vec)2)))
                           )
                     (if(< cosz 1e-8)T
                       (if(<(+(caddr pp)(-(caddr p))(/ rr cosz))allow_cover_temp)
                           (progn
                             (setq dist_normal(apply '+(mapcar '* vec_normal p))
                                   entna(make_2pdimension
                                         nil(list pp(mapcar '+ p(list 0 0(/ rr cosz)))
                                                  vec_normal dist_normal nil(* 0.5 pi)0.
                                                  "CD=<>" str_dimstyle_ductlevel))
                                   vnam(vlax-ename->vla-object entna)
                                   ls_vnam_tempinfluence
                                   (cons vnam ls_vnam_tempinfluence)
                                   )

                             (vla-put-Arrowhead1Type vnam 6)
                             (vla-put-Arrowhead2Type vnam 6)
                             (vla-put-ArrowheadSize vnam(max 0.1(* 0.1 allow_cover_temp)))
                             (vla-put-ExtLine1Suppress vnam -1)
                             (vla-put-ExtLine2Suppress vnam -1)
                             (vla-put-Textgap vnam(max 0.01(* 0.01 allow_cover_temp)))
                             (vla-put-TextHeight vnam(max 0.04(* 0.04 allow_cover_temp)))
                             
                             (vla-put-color vnam int_colcoverng_temp)
                             (addkillobj vnam)
                             )))
                     )
                  ls_p)
               )
             
             (if(and(vl-position int_execute_influence(list 2 3))vnam_line rr)
                 (progn
                   (setq vnam
                         (vla-CopyObjects
                          (vla-get-ActiveDocument(vlax-get-acad-object))
                          (vlax-make-variant
                           (vlax-safearray-fill
                            (vlax-make-safearray vlax-vbObject (cons 0 0))
                            (list vnam_line)))
                          (vla-get-ModelSpace(vla-get-ActiveDocument(vlax-get-acad-object)))
                          )
                         vnam(car(vlax-safearray->list(vlax-variant-value vnam)))
                         ls_solidinfluence(cons(cons rr(cons vnam ls_p))ls_solidinfluence)
                         )
                   (addkillobj vnam)
                   ) )
             
             )
          ls_vnam_select)

         
         (if(vl-position int_execute_influence(list 2 3))
             ((lambda(ls_origin
                      / ls_another v0 v1 vnam r0 r1 ls_pc vec0 vec1 ls_vec0
                      vec_close dist_close
                      )
                (while ls_origin
                  (setq ls_p(car ls_origin)ls_origin(cdr ls_origin)
                        r0(car ls_p)v0(cadr ls_p)ls_p(cddr ls_p)
                        ls_another ls_origin
                        ls_vec0(mapcar '(lambda(p)(xvla-normal v0 p))ls_p)
                        )
                  
                  (while ls_another
                    (setq lst(car ls_another)ls_another(cdr ls_another)
                          r1(car lst)v1(cadr lst)
                          )
                    (mapcar
                     '(lambda(p vec0 / vec p_close d cosz sinh)
                        (setq p_close(vlax-curve-getclosestpointto v1 p nil))
                        (if(cond
                            ((<(setq dist_close(distance p p_close))
                               (+ r0 r1 allow_influence_temp))
                             T)
                            (T nil)
                            
                            ((progn;;直角でない方向を考えていたが不要
                               (setq vec_close(mapcar '- p_close p)
                                     vec_close(mapcar '(lambda(a)(/ a dist_close))vec_close))
                               (<(setq sinh(distance(cross_product vec_close vec0)(list 0 0 0)))1e-8)
                               )
                             nil)
                            ((progn
                               (setq dist_close(- dist_close(/ r0 sinh))
                                     vec1(xvla-normal v1 p_close))
                               (<(setq sinh(distance(cross_product vec_close vec1)(list 0 0 0)))1e-8)
                               )
                             nil)
                            (T
                             (setq dist_close(- dist_close(/ r1 sinh)))
                             (< dist_close allow_influence_temp)
                             )
                            
                            )
                            (progn
                              (setq vec_normal(cross_product(mapcar '- p p_close)vec_view)
                                    vec_normal
                                    (if(<(distance(list 0 0 0)vec_normal)1e-8)
                                        (unit_vector(cross_product(mapcar '- p p_close)vec_x_onview))
                                      (unit_vector(cross_product vec_normal(mapcar '- p p_close))))
                                    )
                              
                              (setq dist_normal(apply '+(mapcar '* vec_normal p))
                                    entna(make_2pdimension
                                          nil(list p p_close vec_normal dist_normal nil
                                                   ((lambda(p0 p1)
                                                      (angle(carxy p0)(carxy p1)) )
                                                    (trans-x p(list 0 0 1)vec_normal)
                                                    (trans-x p_close(list 0 0 1)vec_normal))
                                                   0. "IR=<>" str_dimstyle_ductlevel))
                                    vnam(vlax-ename->vla-object entna)
                                    ls_vnam_tempinfluence
                                    (cons vnam ls_vnam_tempinfluence)
                                    )

                              (vla-put-Arrowhead1Type vnam 6)
                              (vla-put-Arrowhead2Type vnam 6)
                              (vla-put-ArrowheadSize vnam(max 0.1(* 0.1 allow_influence_temp)))
                              (vla-put-ExtLine1Suppress vnam -1)
                              (vla-put-ExtLine2Suppress vnam -1)
                              (vla-put-ExtLineFixedLenSuppress vnam -1)
                              (vla-put-ForceLineInside vnam -1)
                              (vla-put-TextGap vnam(max 0.01(* 0.01 allow_influence_temp)))
                              (vla-put-TextHeight vnam(max 0.04(* 0.04 allow_influence_temp)))
                              (vla-put-TextInside vnam -1)
                              (vla-put-TextInsideAlign vnam 0)
                              (vla-put-TextOutsideAlign vnam 0)
                              (vla-put-VerticalTextPosition vnam 1)

                              
                              (vla-put-color vnam int_colinfluence_temp)
                              (addkillobj vnam)
                              
                              ))
                        )
                     ls_p ls_vec0)
                    
                    
                    
                    
                    )
                  )
                )
              ls_solidinfluence)
           )
         
         
         )
        ((= int_execute_influence 32)
         (mapcar '(lambda(vnam)(exckillobj vnam))ls_vnam_tempinfluence)
         (setq ls_vnam_tempinfluence nil bool_default T)
         
         )
        (T(setq bool_default T) )
        )
       (setq int_execute_influence nil)
       (if bool_default T
         (progn
           (mapcar '(lambda(v)(vla-Highlight v :vlax-false))ls_vnam_select)
           (setq ls_vnam_select nil ls_vnam_highlight nil)
           ))
       
       
       ))
    
    )

   (list
    "influencepoint"
    (cons
     "INITIAL"
     (lambda(bool);;initial
       (if(car bool)
           (progn
             ;;temp
             (setq bool_point nil
                   bool_selectent nil bool_select nil int_selectmode -1
                   
                   textheight_tempobj  0.2
                   vnam_center nil
                   vec_view_project_temp nil
                   )
             
             (setq ls_vnam_tempinfluence(list)
                   int_execute_influence nil)
             (setq
              func_guidemenu
              (lambda()
                ;;調べたい管路を選択→管路上の点を選択
                ;;作成されるテキストは独立したオブジェクトであり、管路の変形に追従しません
                ;;\nまたERASEコマンド等で操作しても管路オブジェクトに影響はありません
                (mix_strasc
                 (list 35519 12409 12383 12356 31649 36335 12434 36984 25246 8594 31649 36335 19978 12398 28857 12434 36984 25246
                       "\n" 20316 25104 12373 12428 12427 12486 12461 12473 12488 12399 29420 31435 12375 12383 12458 12502 12472 12455 12463 12488 12391 12354 12426 12289 31649 36335 12398 22793 24418 12395 36861 24467 12375 12414 12379 12435
                       "\n" 12414 12383 "ERASE" 12467 12510 12531 12489 31561 12391 25805 20316 12375 12390 12418 31649 36335 12458 12502 12472 12455 12463 12488 12395 24433 38911 12399 12354 12426 12414 12379 12435 
                       )
                 ) )

              
              ls_guideexplane
              (mapcar
               'mix_strasc
               (list(list 35519 12409 12383 12356 31649 36335 12434 36984 25246 8594 31649 36335 19978 12398 28857 12434  12463 12522 12483 12463 )
                    ;;管路選択時にEnterで現在の選択を解除
                    (list 31649 36335 36984 25246 26178 12395 "Enter" 12391 29694 22312 12398 36984 25246 12434 35299 38500 )
                    )
               )
              
              ls_guidemenu
              (list
               (list(list 76);; 地表面標高
                    (cons "ITEM"(list 22320 34920 38754 27161 39640))
                    (cons "STATUS"
                          (lambda()
                            (if str_lasground
                                (mix_strasc
                                 (list "{\\C" str_gcol_c ";" 12487 12540 12479 "} : "
                                       (vl-string-subst "" "lasgrid-" str_lasground)))
                              (if height_ground
                                  (mix_strasc
                                   (list"{\\C" str_gcol_g ";" 27161 39640 "} : "
                                        (as-numstr height_ground)))
                                (mix_strasc
                                 (list "{\\C" str_gcol_r ";"
                                       36984 25246 12373 12428 12390 12356 12414 12379 12435 "}"))
                                ))
                            ))
                    (cons "LOADFUNCTION"(lambda()(settile_selectground)))
                    (cons "HELP"(lambda()(mix_strasc(list 20351 29992 12377 12427 27161 39640 12434 "\n- las" 35501 36796 "\n- xml" 35501 36796 "\n- " 19968 23450 27161 39640 12398 25968 20516 20837 21147 "\n" 12363 12425 36984 25246 12391 12365 12414 12377 ))))
                    )
               
               (list(list 67);;文字サイズ
                    (cons "ITEM"(list  25991 23383 12469 12452 12474 ))
                    (cons "INPUT"(lambda() 'textheight_tempobj ))

                    
                    )
               
               
               (list(list nil)
                    (cons "ITEM"(list ))
                    (cons "BOOL"
                          (lambda()
                            T
                            ))
                    (cons
                     "STATUS"
                     (lambda( / bool_depth ii ls_out)
                       (if vnam_center
                           (list(list(mix_strasc(list "{\\C" str_gcol_y ";"
                                                      9733 "  " 36984 25246 20013 "}")))))
                       ))
                    )
               
               (list(list "ENTER");;メインメニューへ
                    (cons "ITEM"(list 12513 12452 12531 12513 12491 12517 12540 12408))
                    (cons "LOADFUNCTION"
                          (lambda()
                            (mapcar '(lambda(vnam)
                                       (vla-delete vnam)
                                       (exckillobj vnam) )
                                    ls_vnam_tempinfluence)
                            (setq ls_vnam_tempinfluence nil)
                            ))
                    (cons "NEXTMODE" "home")
                    )
               
               )
              
              )
             
             ))
       
       (if(cadr bool) (list ) )
       ))

    (cons
     "MOVE"
     (lambda()

       (setq p_close nil)
       (if vnam_center
           (if(<(abs(caddr vec_view))1e-8)
               (princ(mix_strasc(list 12371 12398 27231 33021 12399 27700 24179 12499 12517 12540 12391 12399 20351 29992 12391 12365 12414 12379 12435 )))
             (progn
               (if(equal vec_view vec_view_project_temp)T
                 (progn
                   (setq vec_view_project_temp vec_view
                         cosa(caddr vec_view)
                         ls_p_influence_ground
                         (mapcar
                          '(lambda(p / d v)
                             (setq d(/(caddr p)cosa)
                                   v(mapcar '(lambda(a)(* d a))vec_view))
                             (mapcar '- p v)
                             )
                          ls_p_influencepoint)
                         ls_p(apply 'append(mapcar 'carxy ls_p_influence_ground))
                         )
                   
                   (setq array_p(vlax-make-safearray vlax-vbDouble(cons 0 (1-(length ls_p)))))
                   (vlax-safearray-fill array_p ls_p)
                   (vla-put-coordinates vnam_center_ground array_p)
                   ))
               
               (if(setq p_close(vlax-curve-getclosestpointto vnam_center_ground elem_grread nil))
                   (grdraw elem_grread p_close 2))
               
               ) )
         
         )
       )
     )
    
    
    (cons
     "CLICK"
     (lambda( / )
       (if(<(abs(caddr vec_view))1e-8)
           (x-alert(list 12371 12398 27231 33021 12399 27700 24179 12499 12517 12540 12391 12399 20351 29992 12391 12365 12414 12379 12435 ))
         ;;この機能は水平ビューでは使用できません
         (if vnam_center
             (if p_close
                 (progn
                   (vla-put-startpoint vnam_cross_temp(vlax-3d-point p_close))
                   (vla-put-endpoint vnam_cross_temp(vlax-3d-point(mapcar '+ p_close vec_view)))
                   (if(setq p_duct(car(get_inters_point_vna vnam_center vnam_cross_temp 11)))
                       T
                     (setq p_duct(if(<(vlax-curve-get-distatpoint vnam_center_ground p_close)1e-8)
                                     (vlax-curve-getstartpoint vnam_center)
                                   (vlax-curve-getendpoint vnam_center))))
                   (setq vec(xvla-normal vnam_center p_duct))
                   (if(<(setq cosa(sqrt(- 1.(expt(caddr vec)))))1e-8)
                       (x-alert(list 31649 36335 12364 37467 30452 12398 12383 12417 22303 34987 12426 12399 35336 31639 12391 12365 12414 12379 12435 ))
                     ;;管路が鉛直のため土被りは計算できません
                     (progn
                       (setq p_ground(car(project_to_ground
                                          (list p_duct)(list 0. 0. 1.)(list str_lasground height_ground)))
                             p_duct(mapcar '+ p_duct(list 0. 0.(/ radius_duct_temp cosa)))

                             vec(unit_vector(carxyz vec 0.))
                             vec_text(list(cadr vec)(-(car vec))0.)
                             )
                       (if(>(apply '+(mapcar '*(mapcar '- elem_grread p_close)vec_text))0)T
                         (setq vec_text(mapcar '- vec_text)))
                       (setq dist_normal(apply '+(mapcar '* p_duct vec))
                             entna(make_2pdimension
                                   nil(list p_ground p_duct
                                            vec dist_normal nil(* 0.5 pi)0.
                                            "CD=<>" str_dimstyle_ductlevel))
                             vnam(vlax-ename->vla-object entna)
                             depth_cover(-(caddr p_ground)(caddr p_duct))
                             )
                       
                       (vla-put-Arrowhead1Type vnam 6)
                       (vla-put-Arrowhead2Type vnam 6)
                       (vla-put-ArrowheadSize vnam(max 0.1(* 0.1 depth_cover)))
                       (vla-put-ExtLine1Suppress vnam -1)
                       (vla-put-ExtLine2Suppress vnam -1)
                       (vla-put-Textgap vnam(max 0.01(* 0.01 depth_cover)))
                       (vla-put-TextHeight vnam(max 0.04(* 0.04 depth_cover)))
                       
                       (setq vnam(vla-addtext
                                  (vla-get-modelspace(vla-get-activedocument(vlax-get-acad-object)))
                                  (mix_strasc(list 22303 34987 12426 65306(rtos depth_cover 2 3)))
                                  (vlax-3d-point 0. 0. 0.)textheight_tempobj)
                             )
                       (vla-put-Alignment vnam 9)
                       (vla-put-rotation vnam(atan(cadr vec_text)(car vec_text)))
                       (vla-put-TextAlignmentPoint vnam (vlax-3d-point p_ground))
                       ))
                   
                   ))
           (if(if(if(setq set_ent(ssget elem_grread(list(cons 0 "INSERT")(list -3(list "terraduct3d")))))
                     (setq vnam(vlax-ename->vla-object(ssname set_ent 0))))
                  (progn
                    (vla-getXData vnam "terraduct3d" 'array_Type 'array_Data )
                    (setq ls_xdata
                          (if array_data
                              (split_list 0(mapcar 'vlax-variant-value
                                                   (vlax-safearray->list array_data))))
                          )
                    (=(cdr(assoc "terraduct3d" ls_xdata))"DUCTBLOCK")
                    ))
               (progn
                 (setq vnam_select_duct vnam
                       str_bname(vla-get-name vnam)
                       block(vl-catch-all-apply 'vla-Item(list vnam_blocktable str_bname)))

                 (setq radius_duct_temp nil)
                 (vlax-for
                  obj block
                  
                  (if(and radius_duct_temp vnam_center ) T
                    (progn
                      
                      (vla-getXData obj "terraduct3d" 'array_Type 'array_Data )
                      (setq ls_xdata
                            (if array_data
                                (split_list 0(mapcar 'vlax-variant-value
                                                     (vlax-safearray->list array_data))))
                            str_type(cdr(assoc "terraduct3d" ls_xdata))
                            )

                      (cond
                       ((= str_type "DUCTSOLID")
                        (setq radius_duct_temp(* 0.5(cdr(assoc "DIAM" ls_xdata))))
                        )
                       ((= str_type "CENTERLINE")
                        (setq vnam
                              (vla-CopyObjects
                               (vla-get-ActiveDocument(vlax-get-acad-object))
                               (vlax-make-variant
                                (vlax-safearray-fill
                                 (vlax-make-safearray vlax-vbObject (cons 0 0))
                                 (list obj)))
                               (vla-get-ModelSpace(vla-get-ActiveDocument(vlax-get-acad-object)))
                               )
                              vnam_center(car(vlax-safearray->list(vlax-variant-value vnam)))
                              )
                        (addkillobj vnam_center)
                        
                        (setq ls_p_influencepoint
                              (split_list
                               3(vlax-safearray->list(vlax-variant-value(vla-get-coordinates obj))))
                              vec_view_project_temp vec_view
                              cosa(caddr vec_view)
                              ls_p_influence_ground
                              (mapcar
                               '(lambda(p / d v)
                                  (setq d(/(caddr p)cosa)
                                        v(mapcar '(lambda(a)(* d a))vec_view))
                                  (mapcar '- p v)
                                  )
                               ls_p_influencepoint)
                              vnam_center_ground
                              (xvla-lwpoly(apply 'append(mapcar 'carxy ls_p_influence_ground))
                                          (list nil nil :vlax-false))
                              )
                        (addkillobj vnam_center_ground)
                        )
                       )
                      ))
                  )
                 

                 ))
           
           )
         )
       )
     )

       
    (cons
     "KEYBOAD"
     (lambda( / bool_default ls_solidinfluence vec_normal dist_normal)

       (cond
        ((and(or(= elem_grread 13)(= int_grread 25))vnam_center)
         (mapcar '(lambda(sym / vnam)
                    (setq vnam(eval sym))
                    (exckillobj vnam)
                    (vla-delete vnam)
                    (set sym nil)
                    )
                 '(vnam_center vnam_center_ground))
         )
        )

       
       )
     )
    )
   

   
   (list
    "excavation"
    (cons
     "INITIAL"
     (lambda(bool);;initial
       (if(car bool)
           (progn
             ;;temp
             (setq bool_point nil
                   bool_selectent T bool_select T int_selectmode 0
                   ls_ssget(list(cons 0 "INSERT"))
                   xtype_ssget "DUCTBLOCK" xdata_ssget "terraduct3d"
                   )

             
             (setq
              func_guidemenu
              (lambda()
                ;;選択した管路に対して掘削形状を作成できます\n複数選択も可能ですが、
                ;;掘削形状の断面は最初に選択したものの直角方向が基本となります
                (mix_strasc
                 (list 36984 25246 12375 12383 31649 36335 12395 23550 12375 12390 25496 21066 24418 29366 12434 20316 25104 12391 12365 12414 12377
                       "\n" 35079 25968 36984 25246 12418 21487 33021 12391 12377 12364 12289
                       25496 21066 24418 29366 12398 26029 38754 12399 26368 21021 12395 36984 25246 12375 12383 12418 12398 12398 30452 35282 26041 21521 12364 22522 26412 12392 12394 12426 12414 12377
                       
                       )
                 ) )
              
              ls_guideexplane(list)
              ;; (mapcar
              ;;  'mix_strasc
              ;;  (list(list " - " 31649 36335 12434 36984 25246 12375 12390 23455 34892 )
              ;;       ))
              ;;管路を選択して実行
              
              
              ls_guidemenu
              (list
               
               (list(list 76);; 地表面標高
                    (cons "ITEM"(list 22320 34920 38754 27161 39640))
                    (cons "STATUS"
                          (lambda()
                            (if str_lasground
                                (mix_strasc
                                 (list "{\\C" str_gcol_c ";" 12487 12540 12479 "} : "
                                       (vl-string-subst "" "lasgrid-" str_lasground)))
                              (if height_ground
                                  (mix_strasc
                                   (list"{\\C" str_gcol_g ";" 27161 39640 "} : "
                                        (as-numstr height_ground)))
                                (mix_strasc
                                 (list "{\\C" str_gcol_r ";"
                                       36984 25246 12373 12428 12390 12356 12414 12379 12435 "}"))
                                ))
                            ))
                    (cons "LOADFUNCTION"(lambda()(settile_selectground)))
                    (cons "HELP"(lambda()(mix_strasc(list 20351 29992 12377 12427 27161 39640 12434 "\n- las" 35501 36796 "\n- xml" 35501 36796 "\n- " 19968 23450 27161 39640 12398 25968 20516 20837 21147 "\n" 12363 12425 36984 25246 12391 12365 12414 12377 ))))
                    )
               (list(list 67);;法面色
                    (cons "ITEM"(list 27861 38754 33394  ))
                    (cons "INPUTCOLOR"(lambda()
                                        (if int_colexcavation_temp T
                                          (setq int_colexcavation_temp int_colexcavation))
                                        'int_colexcavation_temp))
                    (cons "LOADFUNCTION"
                          (lambda()
                            nil
                            ))
                    )

               (list(list 83);;法勾配
                    (cons "ITEM"(list 27861 21246 37197  ))
                    (cons "INPUT"(lambda()
                                   (if ratio_excavation_temp T
                                     (setq ratio_excavation_temp ratio_excavation))
                                   'ratio_excavation_temp))


                    ;;法勾配「1:X」のXの値を入力
                    (cons "HELP"(lambda()(mix_strasc(list 27861 21246 37197 12300 "1:X" 12301 12398 "X" 12398 20516 12434 20837 21147 (if int_selectmenu str_guide_inputval str_guide_selectval) ))))
                    )
               
               (list(list 87);;水平離隔
                    (cons "ITEM"(list 27700 24179 38626 38548  ))
                    (cons "INPUT"(lambda()
                                   (if offset_excavation_temp T
                                     (setq offset_excavation_temp offset_excavation))
                                   'offset_excavation_temp))
                    ;;選択した管路、保護コンを平面的にみて最外縁から法尻までの距離を入力
                    (cons "HELP"(lambda()(mix_strasc(list 36984 25246 12375 12383 31649 36335 12289 20445 35703 12467 12531 12434 24179 38754 30340 12395 12415 12390 26368 22806 32257 12363 12425 27861 23611 12414 12391 12398 36317 38626 12434 20837 21147  (if int_selectmenu str_guide_inputval str_guide_selectval) ))))
                    )
               
               (list(list 68);;鉛直離隔
                    (cons "ITEM"(list 37467 30452 38626 38548  ))
                    (cons "INPUT"(lambda()
                                   (if separate_excavation_temp T
                                     (setq separate_excavation_temp separate_excavation))
                                   'separate_excavation_temp))
                    ;;
                    (cons "HELP"(lambda()(mix_strasc(list  (if int_selectmenu str_guide_inputval str_guide_selectval) ))))
                    )

               (list(list 70);;生成ピッチ
                    (cons "ITEM"(list 29983 25104 12500 12483 12481  ))
                    (cons "INPUT"(lambda()
                                   (if pitch_excavation_temp T
                                     (setq pitch_excavation_temp pitch_excavation))
                                   'pitch_excavation_temp))
                    ;;
                    (cons "HELP"(lambda()(mix_strasc(list  (if int_selectmenu str_guide_inputval str_guide_selectval) ))))
                    )
               
               
               ;; (list(list nil)
               ;;      (cons "ITEM"(list ))
               ;;      (cons "BOOL"
               ;;            (lambda()
               ;;              T
               ;;              ))
               ;;      (cons
               ;;       "STATUS"
               ;;       (lambda( / bool_depth ii ls_out)
               ;;         (if ls_vnam_select
               ;;             (list(list(mix_strasc(list "{\\C" str_gcol_y ";"
               ;;                                        9733 "  " 36984 25246 20013 "}")))))
               ;;         ))
               ;;      )
               
               (list(list "ENTER");;メインメニューへ
                    (cons "ITEM"(list 12513 12452 12531 12513 12491 12517 12540 12408))
                    (cons "LOADFUNCTION"
                          (lambda()nil ))
                    (cons "NEXTMODE" "home")
                    )
               
               )
              
              )
             
             ))
       
       (if(cadr bool) (list ) )
       ))

    ;;MOVE
    (cons
     "CLICK"
     (lambda()
       
       nil
       
       )
     )

    (cons
     "KEYBOAD"
     (lambda( / bool_default ls_solidinfluence vec_normal dist_normal)
       (cond
        ((or(= elem_grread 13)(= int_grread 25))
         
         (setq ls_ductroad(list))
         (while ls_vnam_select
           (setq vnam(car ls_vnam_select) ls_vnam_select(cdr ls_vnam_select))
           
           (setq radius_duct_temp nil vnam_center nil ls_pcenter nil
                 wifth_protect_temp nil height_protect_temp nil
                 )
           
           (vlax-for
            obj
            (vla-Item(vla-get-Blocks (vla-get-ActiveDocument(vlax-get-acad-object)))
                     (vla-get-name vnam))
            
            (vla-getXData obj "terraduct3d" 'array_Type 'array_Data )
            (setq ls_xdata
                  (if array_data
                      (split_list 0(mapcar 'vlax-variant-value
                                           (vlax-safearray->list array_data))))
                  str_type(cdr(assoc "terraduct3d" ls_xdata))
                  )
            
            (cond
             ((= str_type "DUCTSOLID")
              (setq radius_duct_temp(* 0.5(cdr(assoc "DIAM" ls_xdata))))
              )
             ((= str_type "CENTERLINE")
              (setq ls_pcenter(vlax-safearray->list(vlax-variant-value(vla-get-coordinates obj)))
                    ls_pcenter(split_list 3 ls_pcenter)
                    vnam
                    (vla-CopyObjects
                     (vla-get-ActiveDocument(vlax-get-acad-object))
                     (vlax-make-variant
                      (vlax-safearray-fill
                       (vlax-make-safearray vlax-vbObject (cons 0 0))
                       (list obj)))
                     (vla-get-ModelSpace(vla-get-ActiveDocument(vlax-get-acad-object)))
                     )
                    vnam_center(car(vlax-safearray->list(vlax-variant-value vnam)))
                    )
              (addkillobj vnam_center)
              
              (setq vnam(xvla-lwpoly(apply 'append(mapcar 'carxy ls_pcenter))(list nil nil :vlax-false)) )
              (addkillobj vnam)
              )
             ((= str_type "MESH")

              (setq width_protect_temp(* 0.5(cdr(assoc "WIDTH" ls_xdata)))
                    height_protect_temp(* 0.5(cdr(assoc "WIDTH" ls_xdata))))
              )
             )
            )

           (if(and radius_duct_temp ls_pcenter)
               (setq ls_ductroad
                     (cons(list vnam vnam_center
                                (if width_protect_temp width_protect_temp radius_duct_temp)
                                (if height_protect_temp height_protect_temp radius_duct_temp))
                          ls_ductroad))
             )
           
           )

         (if((lambda(ls_dummy / vnam1 vnam2 bool)
               (setq bool T)
               (while(and bool ls_dummy)
                 (setq vnam1(caar ls_dummy)
                       ls_dummy(cdr ls_dummy)
                       bool
                       (apply 'and
                              (mapcar '(lambda(lst)
                                         (setq vnam2(car lst))
                                         (null(car(get_inters_point_vna vnam1 vnam2 11)))
                                         )
                                      ls_dummy))
                       )
                 )
               bool)
             ls_ductroad)
             
             (progn
               
               (setq vnam_center_plane(caar ls_ductroad)
                     dist_road(vla-get-length vnam_center_plane)
                     num(1+(fix(/ dist_road pitch_excavation_temp)))
                     delta_road(/ dist_road num)
                     dist_road 0.
                     sum_vol 0.
                     area0 nil p_textinsertion nil
                     )

               (setq ls_pmesh
                     (mapcar
                      '(lambda(i / vnam_normal p_road vec vecx x_min x_max z_min xx  )
                         (if(setq p_road(vlax-curve-getpointatdist vnam_center_plane dist_road))T
                           (setq p_road(vlax-curve-getendpoint vnam_center_plane dist_road)))
                         
                         (setq dist_road(+ dist_road delta_road)
                               vec_normal(xvla-normal vnam_center_plane p_road)
                               vecx(trans-x(list -1 0 0)vec_normal(list 0 0 1))
                               vnam_normal
                               (vla-addline(vla-get-modelspace(vla-get-activedocument(vlax-get-acad-object)))
                                           (vlax-3d-point p_road) (vlax-3d-point(mapcar '+ p_road vecx))
                                           )
                               )
                         
                         (addkillobj vnam_normal)
                         
                         (mapcar
                          '(lambda(lst / vnam vnam_center ww hh p xx x0 x1 zz p_road ls_p)
                             (setq vnam(car lst)vnam_center(cadr lst)
                                   ww(caddr lst)hh(cadddr lst)
                                   )
                             
                             (if(setq ls_p(get_inters_point_vna vnam_normal vnam 11) )
                                 (progn
                                   (setq ls_p(mapcar '(lambda(p / p_close dd)
                                                        (setq p_close
                                                              (vlax-curve-getclosestpointto vnam p nil)
                                                              )
                                                        (list(distance p_close p)p))
                                                     ls_p)
                                         p(cadar(vl-sort ls_p '(lambda(a b)(<(car a)(car b)))))
                                         )
                                   (vla-put-startpoint vnam_cross_temp(vlax-3d-point p))
                                   (vla-put-endpoint vnam_cross_temp(vlax-3d-point(mapcar '+ p(list 0 0 1))))
                                   (if(setq p(car(get_inters_point_vna vnam_center vnam_cross_temp 11)))
                                       (progn
                                         
                                         (setq xx(apply '+(mapcar '* p vecx))
                                               zz(-(caddr p)hh separate_excavation_temp)
                                               x0(- xx ww offset_excavation_temp)
                                               x1(+ xx ww offset_excavation_temp)
                                               )
                                         
                                         (if x_min
                                             (setq z_min(min z_min zz)
                                                   x_min(min x_min x0)x_max(max x_max x1))
                                           (setq z_min zz x_min x0 x_max x1))
                                         ))
                                   ))
                             
                             )
                          ls_ductroad)

                         (setq xx(apply '+(mapcar '* p_road vecx))
                               vec(mapcar '(lambda(a)(* a(- x_min xx)))vecx)
                               p1(carxyz(mapcar '+ p_road vec)z_min)
                               vec(mapcar '(lambda(a)(* a(- x_max xx)))vecx)
                               p2(carxyz(mapcar '+ p_road vec)z_min)
                               vec0(unit_vector(mapcar '(lambda(x z)(+(* ratio_excavation_temp x)z))
                                                       (mapcar '- vecx)(list 0. 0. 1.)))
                               
                               p0(car(project_to_ground
                                      (list p1)vec0(list str_lasground height_ground)))
                               vec1(unit_vector(mapcar '(lambda(x z)(+(* ratio_excavation_temp x)z))
                                                      vecx(list 0. 0. 1.)))
                               p3(car(project_to_ground
                                      (list p2)vec1(list str_lasground height_ground)))
                               )
                         
                         ;; (if(and p0 p3)T
                         ;;   (progn
                         ;;     (setq num_divide 20 recipro_divide 0.05
                         ;;           ls_proj
                         ;;           (mapcar
                         ;;            '(lambda(ii / p v)
                         ;;               (setq p(mapcar '(lambda(a b)
                         ;;                                 (*(+(* ii a)(*(- num_divide ii)b))
                         ;;                                   recipro_divide))
                         ;;                              p1 p2)
                         ;;                     v(mapcar '(lambda(a b)
                         ;;                                 (*(+(* ii a)(*(- num_divide ii)b))
                         ;;                                   recipro_divide))
                         ;;                              vec0 vec1)
                         ;;                     )
                         ;;               (car(project_to_ground
                         ;;                    (list p)v(list str_lasground height_ground)))
                         ;;               )
                         ;;            (inclist 1 num_divide))
                         ;;           ls_proj(vl-remove nil ls_proj)
                         ;;           )
                         
                         
                         
                         (if(and p0 p3)
                             (progn
                               

                               
                               (if p_textinsertion T
                                 (setq p_textinsertion p2 vec_textnormal vec_normal))
                               (setq area1(apply '+(mapcar '(lambda(lst / p1 p2 p3 d1 d2 d3 ss)
                                                              (mapcar 'set '(p1 p2 p3)lst)
                                                              (setq d1(distance p1 p2)
                                                                    d2(distance p2 p3)
                                                                    d3(distance p3 p1)
                                                                    ss(*(+ d1 d2 d3)0.5)
                                                                    )
                                                              (sqrt(*(- ss d1)(- ss d2)(- ss d3)ss))

                                                              )
                                                           (list(list p0 p1 p2)(list p0 p2 p3))))
                                     )
                               (if area0(setq sum_vol(+ sum_vol(* 0.5(+ area0 area1)
                                                                  (*(- i i_prev)delta_road)))))
                               (setq area0 area1 i_prev i)
                               (list p0 p1 p2 p3)
                               
                               )
                           (progn nil)
                           )
                         )
                      (inclist 0(1+ num))
                      )

                     ls_pmesh(vl-remove nil ls_pmesh)
                     )
               
               
               (setq i 0)
               (while
                   (progn
                     (setq str_bname(strcat "DUCTEXCAVATION$"(itoa(setq i(1+ i)))))
                     (null
                      (vl-catch-all-error-p
                       (vl-catch-all-apply 'vla-Item(list vnam_blocktable str_bname))))
                     )
                 )
               (setq block(vla-Add vnam_blockTable(vlax-3d-point 0 0 0)str_bname)
                     ls_vla-release(cons block ls_vla-release))

               (setq numx(length ls_pmesh)
                     numy 4
                     ls_p(apply 'append(apply 'append ls_pmesh))
                     )
               
               (setq array_mesh(vlax-make-safearray vlax-vbDouble(cons 0(1-(length ls_p)))))
               (vlax-safearray-fill array_mesh ls_p)
               (setq vnam (vla-Add3DMesh block numx numy array_mesh) )
               (vla-put-color vnam int_colexcavation_temp)
               

               (setq vnam (vla-addmtext block (vlax-3d-point 0 0 0) 0. "AAA"))
               (mapcar
                '(lambda(lst / func val)
                   (setq func(car lst)val(cadr lst))
                   (func vnam val)
                   )
                (list(list vla-put-textstring
                           (strcat(mix_strasc(list 20307 31309 ":"))
                                  (rtos sum_vol 2 3)
                                  (mix_strasc(list "\n" 21246 37197  " 1:"))
                                  (rtos ratio_excavation_temp 2 1)
                                  (mix_strasc(list "\n" 27700 24179 38626 38548 " "))
                                  (rtos offset_excavation_temp 2 1)
                                  (mix_strasc(list "\n" 24202 20184 12369 38626 38548 " "))
                                  (rtos separate_excavation_temp 2 1)
                                  ))
                     (list vla-put-attachmentpoint 1)
                     (list vla-put-StyleName str_textstyle_gbo)
                     (list vla-put-normal(vlax-3d-point(mapcar '- vec_textnormal)))
                     (list vla-put-insertionpoint(vlax-3d-point p_textinsertion))
                     (list vla-put-height 0.2)
                     )
                )

               (setq vnam(vla-InsertBlock
                          (vla-get-ModelSpace(vla-get-ActiveDocument(vlax-get-acad-object)))
                          (vlax-3d-point 0 0 0)str_bname 1 1 1 0)
                     )
               (set_xda vnam(list(cons 1000 "EXCAVATION")
                                 (cons 1000 "VOLUME")(cons 1040 sum_vol)
                                 (cons 1000 "SLOPE")(cons 1040 ratio_excavation_temp)
                                 (cons 1000 "OFFSET")(cons 1040 offset_excavation_temp)
                                 (cons 1000 "SEPARATE")(cons 1040 separate_excavation_temp)
                                 )
                        "terraduct3d")
               
               )
           
           ;;平面で交している管路が選択されているため掘削形状を決定できません
           (x-alert(list 24179 38754 12391 20132 12375 12390 12356 12427 31649 36335 12364 36984 25246 12373 12428 12390 12356 12427 12383 12417 25496 21066 24418 29366 12434 27770 23450 12391 12365 12414 12379 12435 ))
           )
         
         (mapcar '(lambda(lst / vnam)
                    (setq vnam(car lst))  (exckillobj vnam) (vla-delete vnam)
                    (setq vnam(cadr lst)) (exckillobj vnam) (vla-delete vnam)
                    )
                 ls_ductroad)
         
         (mapcar '(lambda(v)(vla-Highlight v :vlax-false))ls_vnam_highlight)
         (setq ls_vnam_highlight nil)
         )
        )
       
       )
     )
    
    )
   
   (list
    "savecsvifc" ;;edsym
    (cons
     "INITIAL"
     (lambda(bool);;initial
       (if(car bool)
           (progn
             ;;temp
             (setq bool_point nil
                   bool_selectent T bool_select T int_selectmode 0
                   ls_ssget(list(cons 0 "INSERT"))
                   xtype_ssget "DUCTBLOCK,CCBOXBLOCK,CCBOXTEMPBLOCK,MANHOLEBLOCK"
                   xdata_ssget "terraduct3d"
                   ls_vnam_select nil
                   )

             (setq int_overwrite_readcsv 0)
             (setq int_savecsvifc nil)
             
             (setq
              func_guidemenu
              (lambda()
                ;;投影した経路、管路、特殊部を対象に選択でき、その他のものは選択しようとしてもハイライトされません
                ;;\n何も選択しないとき、すべて選択したことになります
                ;;\n選択有り無し
                (mix_strasc
                 (list 25237 24433 12375 12383 32076 36335 12289 31649 36335 12289 29305 27530 37096 12434 23550 35937 12395 36984 25246 12391 12365 12289 12381 12398 20182 12398 12418 12398 12399 36984 25246 12375 12424 12358 12392 12375 12390 12418 12495 12452 12521 12452 12488 12373 12428 12414 12379 12435
                       "\n" 20309 12418 36984 25246 12375 12394 12356 12392 12365 12289 12377 12409 12390 36984 25246 12375 12383 12371 12392 12395 12394 12426 12414 12377
                       "\n" 36984 25246 12304
                       (if ls_vnam_select(list 26377 12426)(list 28961 12375)) 12305
                       )
                 ) )
              
              ls_guideexplane
              (mapcar
               'mix_strasc
               (list(list " - " 25237 24433 12375 12383 32076 36335 12289 31649 36335 12289 29305 27530 37096 12434 23550 35937 12395 36984 25246 12391 12365 12289 12381 12398 20182 12398 12418 12398 12399 36984 25246 12375 12424 12358 12392 12375 12390 12418 12495 12452 12521 12452 12488 12373 12428 12414 12379 12435)
                    (list " - " 20309 12418 36984 25246 12375 12390 12356 12394 12356 12392 12365 22259 38754 20869 12398 12377 12409 12390 12364 23550 35937 12395 12394 12426 12414 12377 )
                    ))
              ;;何も選択していないとき図面内のすべてが対象になります
              
              ls_guidemenu
              (list
               
               (list(list 49);;CSV保存
                    (cons "ITEM"(list "CSV" 20445 23384  ))
                    (cons "NEXTMODE" str_edit);;
                    (cons "LOADFUNCTION"
                          (lambda()(setq str_next nil int_savecsvifc 1) ))
                    (cons "CLICKFUNCTION"
                          (lambda()(setq bool_replacegrread T int_grread 2 elem_grread 49) ))
                    
                    )
               
               (list(list 50);;CSV読込
                    (cons "ITEM"(list "CSV" 35501 36796 ))
                    (cons "NEXTMODE" str_edit);;
                    (cons "LOADFUNCTION"
                          (lambda()(setq str_next nil int_savecsvifc 2) ))
                    (cons "CLICKFUNCTION"
                          (lambda()(setq bool_replacegrread T int_grread 2 elem_grread 50) ))
                    
                    )

               (list(list 51);;CSV読込み時の名称上書き
                    (list "ITEM"(list "CSV" 35501 36796 12415 26178 12398 21517 31216 19978 26360 12365 ))
                    (cons "INPUTSWITCH"
                          (lambda()
                            (list 'int_overwrite_readcsv
                                  (mapcar 'mix_strasc
                                          (list(list "{\\C" str_gcol_y ";" 31105 27490 "}")
                                               (list "{\\C" str_gcol_c ";" 35377 21487 "}")))
                                  )
                            ) )
                    ;;読み込んだ管や特殊部の名称が現在図面内に存在するものと一致するときにどうするか設定してください
                    ;;許可すると現在図面内に存在する同名オブジェクトはすべて削除されます
                    ;;完了時に読み込みできなかったオブジェクト（禁止時）、上書きしたオブジェクト（許可時）を報告し、クリップボードに貼り付けます
                    (cons "HELP"
                          (lambda()
                            (mix_strasc
                             (list 35501 12415 36796 12435 12384 31649 12420 29305 27530 37096 12398 21517 31216 12364 29694 22312 22259 38754 20869 12395 23384 22312 12377 12427 12418 12398 12392 19968 33268 12377 12427 12392 12365 12395 12393 12358 12377 12427 12363 35373 23450 12375 12390 12367 12384 12373 12356
                                   "\n" 35377 21487 12377 12427 12392 29694 22312 22259 38754 20869 12395 23384 22312 12377 12427 21516 21517 12458 12502 12472 12455 12463 12488 12399 12377 12409 12390 21066 38500 12373 12428 12414 12377
                                   "\n" 23436 20102 26178 12395 35501 12415 36796 12415 12391 12365 12394 12363 12387 12383 12458 12502 12472 12455 12463 12488 65288 31105 27490 26178 65289 12289 19978 26360 12365 12375 12383 12458 12502 12472 12455 12463 12488 65288 35377 21487 26178 65289 12434 22577 21578 12375 12289 12463 12522 12483 12503 12508 12540 12489 12395 36028 12426 20184 12369 12414 12377 ))))
                    )
               
               (list(list 52);;IFC保存
                    (cons "ITEM"(list "IFC" 20445 23384  ))
                    (cons "NEXTMODE" str_edit);;
                    (cons "LOADFUNCTION"
                          (lambda()(setq str_next nil int_savecsvifc 3) ))
                    (cons "CLICKFUNCTION"
                          (lambda()(setq bool_replacegrread T int_grread 2 elem_grread 52) ))
                    
                    )
               
               (list(list 80 );;P選択モード切替
                    (cons "ITEM"(list 36984 25246 12514 12540 12489 20999 26367 ))
                    (cons "INPUTSWITCH"
                          (lambda()
                            (if(= int_selectmode -1)
                                (list nil(mix_strasc
                                          (list "{\\C" str_gcol_p ";"
                                                21336 20307 36984 25246 12398 12415 "}")))
                              (list 'int_selectmode
                                    (mapcar 'mix_strasc
                                            (list(list "{\\C" str_gcol_y ";" 36984 25246 "}")
                                                 (list "{\\C" str_gcol_c ";" 35299 38500 "}")))
                                    ))
                            ) )
                    (cons "HELP"(lambda()str_guide_selectmode))
                    )
               
               (list(list nil)
                    (cons "ITEM"(list ))
                    (cons "BOOL"
                          (lambda()
                            nil
                            ))
                    (cons "STATUS" (lambda( / bool_depth ii ls_out) "" ))
                    )
               
               (list(list "ENTER");;メインメニューへ
                    (cons "ITEM"(list 12513 12452 12531 12513 12491 12517 12540 12408))
                    (cons "NEXTMODE" "home")
                    )
               
               )
              
              
              )
             
             ))
       
       (if(cadr bool) (list ) )
       ))
    
    
    (cons
     "KEYBOAD"
     (lambda( / ls_str_out num ls_out_parameter str_out bool_loop)
       
       (cond
        ((null int_savecsvifc))
        ((vl-position int_savecsvifc(list 1 3))
         
         (princ(mix_strasc(list "\n" 22259 38754 20869 12398 24773 22577 12434 38598 12417 12390 12356 12414 12377 "..." 12362 24453 12385 12367 12384 12373 12356 "...\n") ))
         ;;図面内の情報を集めています...お待ちください...
         (if ls_vnam_select T
           ((lambda( / num ls_out vnam)
              (setq set_ent(ssget "X"(list(cons 0 "INSERT")(list -3(list "terraduct3d"))))
                    num(if set_ent(sslength set_ent)0) )
              (while(>(setq num(1- num))-1)
                (setq vnam(vlax-ename->vla-object(ssname set_ent num))
                      ls_vnam_select(cons vnam ls_vnam_select))
                )
              ))
           )
         
         (if(= int_savecsvifc 1)
             (setq ls_str_out
                   (list "DATA"))
                    ;; (mix_strasc;;読込時にEXPLANE列は不要で、DATA列より右が必要です
                    ;;  (list "EXPLANE,DATA," 35501 36796 26178 12395 "EXPLANE" 21015 12399
                    ;;        19981 35201 12391 12289 "DATA" 21015 12424 12426
                    ;;        21491 12364 24517 35201 12391 12377 )))) )
           (setq ls_ifcparameter
                 (list "type" "name" "r" "g" "b" "properties" "x" "y" "z" "dx" "dy" "radius" "thickness"
                       "ex" "ey" "ez" "rotate" "height" "shapename" "face" "xx" "rebar")
                 ls_str_out
                 (cons(substr(apply 'strcat(mapcar '(lambda(str)(strcat "," str))ls_ifcparameter))2)
                      ls_str_out)
                 )
           )

         (setq ls_str_out_duct(list)
               ls_str_out_ccbox(list)
               ls_str_out_road(list)
               ls_str_out_temp(list);;テンプレートから作った特殊部・マンホール
               )
         
         (mapcar
          '(lambda(vnam)
             (vla-getXData vnam "terraduct3d" 'array_Type 'array_Data )
             (setq ls_xdata
                   (if array_data
                       (split_list 0(mapcar 'vlax-variant-value
                                            (vlax-safearray->list array_data))))
                   str_type(cdr(assoc "terraduct3d" ls_xdata))
                   )

             (vla-getXData vnam "attributedata" 'array_Type 'array_Data )
             (setq ls_xdata_att
                   (if array_data
                       (mapcar '(lambda(lst)(strcat(car lst)","(cadr lst)))
                               (split_list 2(cdr(mapcar 'vlax-variant-value
                                                        (vlax-safearray->list array_data)))) ))
                   )

             ;; (setq p_insert(vlax-safearray->list(vlax-variant-value(vla-get-insertionpoint vnam)))
             ;;       rotation_insert(vla-get-rotation vnam)
             ;;       vec_insert(vlax-safearray->list(vlax-variant-value(vla-get-normal vnam)))
             ;;       x_scale(vla-get-XScaleFactor vnam)
             ;;       transMat(vlax-tmatrix (list(list 0 -1 0 0)
             ;;                                  (list 1 0 0 0)
             ;;                                  (list 0 0 1 0)
             ;;                                  (list 0 0 0 1)))
             ;;       )
             ;; (vla-scaleentity vnam(vlax-3d-point 0 0 0)x_scale)
             ;; (vla-Rotate3D vnam(vlax-3d-point 0 0 0)(vlax-3d-point 0 0 1) rotation_insert)
             ;; (vla-Move vnam(vlax-3d-point 0 0 0)(vlax-3d-point p_insert))
             ;; ;; (vla-TransformBy vnam transMat)

             (setq str(vla-get-name vnam)
                   vnam(vla-Item(vla-get-Blocks (vla-get-ActiveDocument(vlax-get-acad-object)))str)
                   ls_out_parameter(list)
                   ls_search(list) num_min nil num_max nil
                   )
             
             (cond
              ((= str_type "DUCTBLOCK")
               (if(= int_savecsvifc 1)
                   (setq str_out(strcat "DUCTBLOCK," str) )
                 (setq ls_out_parameter(cons(cons "NAME" str)ls_out_parameter))
                 )
               
               (vlax-for
                obj vnam
                (vla-getXData obj "terraduct3d" 'array_Type 'array_Data )
                (setq ls_xdata
                      (if array_data
                          (split_list 0(mapcar 'vlax-variant-value
                                               (vlax-safearray->list array_data))))
                      str_type(cdr(assoc "terraduct3d" ls_xdata))
                      )
                
                (cond
                 ((or(= str_type "DEPTH")(= str_type "ARC"))
                  (setq int_line(cdr(assoc "NUM" ls_xdata))
                        int_side(cdr(assoc "SIDE" ls_xdata))
                        )
                  (if num_min(setq num_min(min num_min int_line)
                                   num_max(max num_max int_line))
                    (setq num_min int_line num_max int_line))
                  (setq lst(cons(list str_type int_line int_side)
                                (cons(cons "OBJ"(vlax-vla-object->ename obj))ls_xdata))
                        ls_search(cons lst ls_search))
                  )
                 ((= str_type "DUCTSOLID")
                  
                  (setq ls_out_parameter
                        (cons(assoc "DIAM" ls_xdata)ls_out_parameter)
                        )
                  (if(= int_savecsvifc 1)
                      (setq ls_out_parameter
                            (cons(cons "COLDUCT"(vla-get-color obj))ls_out_parameter)
                            )
                    (setq ls_out_parameter
                          (cons(cons "TCOLDUCT"
                                     ((lambda(vtc)
                                        (mapcar '(lambda(a)(a vtc))
                                                (list vla-get-red vla-get-green vla-get-blue)))
                                      (vla-get-truecolor obj)))
                               ls_out_parameter)
                          )
                    )
                  
                  )
                 ((= str_type "CONMESH")
                  
                  (setq ls_out_parameter
                        (cons(cons "COLCON"(vla-get-color obj))ls_out_parameter) )
                  (if(= int_savecsvifc 1)
                      (setq ls_out_parameter
                            (cons(cons "TYPE"(if(<(cdr(assoc "CORNER" ls_xdata))0)1 0))ls_out_parameter)
                            ls_out_parameter
                            (cons(assoc "WIDTH" ls_xdata)ls_out_parameter)
                            ls_out_parameter
                            (cons(assoc "HEIGHT" ls_xdata)ls_out_parameter)
                            ls_out_parameter
                            (cons(assoc "FILET" ls_xdata)ls_out_parameter)
                            )
                    (setq ls_out_parameter(cons(cons "MESHOBJ" obj)ls_out_parameter)
                          ls_out_parameter
                          (cons(cons "TCOLMESH"
                                     ((lambda(vtc)
                                        (mapcar '(lambda(a)(a vtc))
                                                (list vla-get-red vla-get-green vla-get-blue)))
                                      (vla-get-truecolor obj)))
                               ls_out_parameter)
                          )
                    
                    )
                  )
                 ((= str_type "CENTERLINE")
                  (setq ls_out_parameter(cons(cons "CENTERLINE" obj)ls_out_parameter))
                  
                  )
                 )
                )

               (if(= int_savecsvifc 1)
                   (progn
                     (mapcar
                      '(lambda(lst / str str_initial)
                         (if(setq str(cdr(assoc(car lst)ls_out_parameter)))T
                           (setq str(cadr lst)))
                         (setq str_out(strcat str_out ","(as-numstr str))))
                      (list(list "COLDUCT")(list "COLCON")
                           (list "DIAM" diam_duct)(list "TYPE" 2)
                           (list "WIDTH" width_protect)
                           (list "HEIGHT" height_protect)
                           (list "FILET" filet_protect)
                           )
                      )
                     (setq ls_str_out_duct(cons(strcat str_out)ls_str_out_duct)
                           ls_str_out_duct
                           (cons(strcat "ATTRIBUTE"
                                        (apply 'strcat
                                               (mapcar '(lambda(str)(strcat "," str))
                                                       ls_xdata_att
                                                       )))
                                ls_str_out_duct)
                           )
                     )
                 )
               
               (setq num_min(1- num_min) ls_line(list)
                     ls_roadfrominsert(list)
                     num_temp num_min
                     str_out ""
                     )

               
               (if(= int_savecsvifc 1)
                   (while(<=(setq num_temp(1+ num_temp))num_max)
                     
                     (mapcar
                      '(lambda(int_side / ls_gcode)
                         (setq lst(assoc(list "DEPTH" num_temp int_side)ls_search)
                               ls_search(vl-remove lst ls_search)
                               hand_road(cdr(assoc "ROAD" lst))
                               ls_gcode(entget(cdr(assoc "OBJ" lst)))
                               )

                         (setq str_out(apply
                                       'strcat
                                       (mapcar
                                        '(lambda(ii / lst)
                                           (setq lst(cdr(assoc ii ls_gcode)))
                                           (if(=(type lst)'LIST)
                                               (apply
                                                'strcat
                                                (mapcar '(lambda(a)(strcat(as-numstr a)"," ))lst))
                                             (strcat(as-numstr lst)","))
                                           )
                                        (list 13 14 3)))
                               str_out(strcat "DEPTH," str_out(if hand_road hand_road ""))
                               ls_str_out_duct(cons str_out ls_str_out_duct)
                               )
                         
                         )
                      (list 0 1))
                     
                     
                     (if(assoc(list "ARC" num_temp 0)ls_search)
                         (mapcar
                          '(lambda(int_side / ls_gcode)
                             (setq lst(assoc(list "ARC" num_temp int_side)ls_search)
                                   ls_search(vl-remove lst ls_search)
                                   ls_gcode(entget(cdr(assoc "OBJ" lst)))
                                   str_out(apply
                                           'strcat
                                           (mapcar
                                            '(lambda(ii / lst)
                                               (setq lst(cdr(assoc ii ls_gcode)))
                                               (if(=(type lst)'LIST)
                                                   (apply
                                                    'strcat
                                                    (mapcar '(lambda(a)(strcat(as-numstr a)","))lst))
                                                 (strcat(as-numstr lst)","))
                                               )
                                            (list 15 13 14 10 11 210 3)))
                                   str_out(strcat "ARC," str_out)
                                   ls_str_out_duct(cons str_out ls_str_out_duct)
                                   )
                             )
                          (list 0 1))
                       )
                     )
                 
                 
                 (if T
                     (progn;;REBARTYPE
                       (setq lst(assoc(list "DEPTH"(1+ num_temp)0)ls_search)
                             ls_search(vl-remove lst ls_search)
                             ls_gcode(entget(cdr(assoc "OBJ" lst)))
                             str_out ""
                             )
                       (mapcar '(lambda(a)(setq str_out(strcat str_out ","(as-numstr a))))
                               (cdr(assoc 14 ls_gcode)))
                       (setq str_out(substr str_out 2))
                       
                       (while(assoc(list "ARC"(setq num_temp(1+ num_temp))0)ls_search)
                         (mapcar
                          '(lambda(int_side / ls_gcode)
                             (setq lst(assoc(list "ARC" num_temp int_side)ls_search)
                                   ls_search(vl-remove lst ls_search)
                                   ls_gcode(entget(cdr(assoc "OBJ" lst)))
                                   )
                             
                             (mapcar
                              '(lambda(lst)
                                 (setq str_out(strcat str_out(car lst)))
                                 (mapcar '(lambda(a)(setq str_out(strcat str_out ","(as-numstr a))))
                                         (cdr lst))
                                 )
                              (list
                               (if(= int_side 0)
                                   (cons "|POLY" (cdr(assoc 13 ls_gcode)))
                                 (list ""))
                               (cons "|ARC"(cdr(assoc 14 ls_gcode)))
                               (cons "" (cdr(assoc 15 ls_gcode)))
                               )
                              )
                             
                             )
                          (list 0 1))
                         )

                       (setq lst(assoc(list "DEPTH" num_temp 1)ls_search)
                             ls_search(vl-remove lst ls_search)
                             ls_gcode(entget(cdr(assoc "OBJ" lst)))
                             str_out(strcat str_out "|POLY")
                             )
                       
                       (mapcar '(lambda(a)(setq str_out(strcat str_out ","(as-numstr a)) ))
                               (cdr(assoc 14 ls_gcode)))
                       
                       (setq ls_out_parameter(cons(cons "REBAR" str_out)ls_out_parameter))
                       
                       )
                   (progn;;FACETYPE
                     
                     
                     
                     
                     )
                   )
                 )
               
               (if(= int_savecsvifc 1)
                   (setq ls_str_out_duct(cons "DUCTBLOCKEND," ls_str_out_duct)
                         
                         )


                 (if nil
                     (progn;;REBARTYPE
                       (setq ls_rgb(cdr(assoc "TCOLDUCT" ls_out_parameter))
                             str(apply
                                 'strcat
                                 (mapcar
                                  '(lambda(str / strx strc)
                                     (setq strx
                                           (cond
                                            ((= str "type")"REBAR")
                                            ((= str "name")(cdr(assoc "NAME" ls_out_parameter)))
                                            ((= str "r")(as-numstr(/(car ls_rgb)255.)))
                                            ((= str "g")(as-numstr(/(cadr ls_rgb)255.)))
                                            ((= str "b")(as-numstr(/(caddr ls_rgb)255.)))
                                            ((= str "properties")
                                             (strcat
                                              "\""
                                              (substr (apply 'strcat
                                                             (mapcar '(lambda(str)(strcat "|" str))
                                                                     ls_xdata_att))
                                                      2)
                                              "\"")
                                             )
                                            ((= str "radius")
                                             (as-numstr(* 0.5(cdr(assoc "DIAM" ls_out_parameter)))))
                                            ((= str "rebar")
                                             (strcat "\""(cdr(assoc "REBAR" ls_out_parameter))"\""))
                                            (T "")
                                            )
                                           )
                                     (strcat "," strx))
                                  ls_ifcparameter))
                             ls_str_out(cons(substr str 2)ls_str_out)
                             )
                       )
                   (progn

                     (progn;;bool_loop
                       (setq vnam(cdr(assoc "CENTERLINE" ls_out_parameter))
                             ls_p(vlax-safearray->list(vlax-variant-value(vla-get-coordinates vnam)))
                             numy 32
                             
                             ls_rgb(cdr(assoc "TCOLDUCT" ls_out_parameter))
                             
                             ls_p(split_list 3 ls_p)
                             
                             str(apply
                                 'strcat
                                 (mapcar
                                  '(lambda(str / strx)
                                     (setq strx
                                           (cond
                                            ((= str "type")"FACEUNION")
                                            ((= str "name")(cdr(assoc "NAME" ls_out_parameter)))
                                            ((= str "r")(as-numstr(/(car ls_rgb)255.)))
                                            ((= str "g")(as-numstr(/(cadr ls_rgb)255.)))
                                            ((= str "b")(as-numstr(/(caddr ls_rgb)255.)))
                                            ((= str "properties")
                                             (strcat
                                              "\""
                                              (substr (apply 'strcat
                                                             (mapcar '(lambda(str)(strcat "|" str))
                                                                     ls_xdata_att))
                                                      2)
                                              "\"")
                                             )
                                            (T(setq str ""))
                                            ))
                                     (strcat "," strx))
                                  ls_ifcparameter))

                             ls_str_out(cons(substr str 2)ls_str_out)
                             )

                       (setq ls_dummy ls_p vec0 nil ls_p(list) p1 nil)
                       (while ls_dummy
                         (setq p0(car ls_dummy)ls_dummy(cdr ls_dummy))
                         (if(setq p1(car ls_p))
                             (setq vec1(unit_vector(mapcar '- p0 p1))
                                   d(distance p0 p1))
                           (setq d 0))
                         (if(or(if(and vec0 vec1)
                                   (>(abs(1-(apply '+(mapcar '* vec0 vec1))))1e-8))
                               (> d 4.)
                               (<(length ls_p)2)
                               )
                             (setq ls_p(cons p0 ls_p))
                           (setq ls_p(cons p0(cdr ls_p))))
                         (setq vec0 vec1 )
                         )
                       
                       (setq ii 0 num(1-(length ls_p))
                             ls_intmesh(inclist 0 numy)
                             ang_d(/(* 2. pi)numy)
                             r(* 0.5(cdr(assoc "DIAM" ls_out_parameter)))
                             vecxp nil vecyp nil
                             )

                       
                       (setq ls_p(mapcar
                                  '(lambda(p / vec vecx vecy)
                                     (setq vec(xvla-normal vnam p)
                                           vecx(trans-x(list -1 0 0)vec(list 0 0 1))
                                           vecy(trans-x(list 0 1 0)vec(list 0 0 1))
                                           )
                                     (if(if vecxp(>(apply '+(mapcar '* vecx vecxp))0)T)T
                                       (setq vecx vecxp))
                                     (setq vecxp vecx)
                                     (if(<(caddr vecy)0)(setq vecy(mapcar '- vecy)))
                                     
                                     (mapcar '(lambda(i / c s)
                                                (setq c(cos(* ang_d i))s(sin(* ang_d i)))
                                                (mapcar '(lambda(a x y)(+(* r c x)(* r s y)a))
                                                        p vecx vecy))
                                             ls_intmesh)
                                     )
                                  ls_p)
                             
                             )


                       (mapcar;;すごく時間がかかる
                        '(lambda(lst1 lst2 / p01 p02 p03 p04 p11 p12 p13 p14 ls_pmesh jj)
                           ;;(mapcar 'set '(p01 p02 p03 p04)lst1)
                           ;;(mapcar 'set '(p11 p12 p13 p14)lst2)

                           (setq ii(1+ ii)str_p "" i 0 
                                 ls_p_mesh
                                 (mapcar '(lambda(j / p01 p02 p11 p12)
                                            (setq p01(nth(rem j numy)lst1)
                                                  p02(nth(rem(1+ j)numy)lst1)
                                                  p11(nth(rem j numy)lst2)
                                                  p12(nth(rem(1+ j)numy)lst2))
                                            (list p01 p02 p11 p02 p12 p11)
                                            )
                                         ls_intmesh )
                                 ls_p_mesh
                                 (apply 'append(apply 'append ls_p_mesh))
                                 ;;(if(= ii 1)(append p01 p04 p02 p04 p03 p02))
                                 ;;(if(= ii num)(append p14 p11 p13 p11 p12 p13))
                                 
                                 )
                           (mapcar '(lambda(a )
                                      (setq i(1+ i)
                                            str_p(strcat str_p(if(=(rem i 9)1)"|" ",")
                                                         (as-numstr a))
                                            ))
                                   ls_p_mesh)
                           
                           (setq str_p(strcat "\""(substr str_p 2)"\"")
                                 str(apply 'strcat
                                           (mapcar '(lambda(str)
                                                      (if(= str "type")(setq str "FACE")
                                                        (if(= str "face")(setq str str_p)
                                                          (setq str "")))
                                                      (strcat "," str))
                                                   ls_ifcparameter))
                                 ls_str_out(cons(substr str 2) ls_str_out)
                                 )
                           )
                        ls_p(cdr ls_p))
                       
                       (setq str(apply 'strcat
                                       (mapcar '(lambda(str)
                                                  (if(= str "type")(setq str "FACEEND")
                                                    (setq str ""))
                                                  (strcat "," str))
                                               ls_ifcparameter))
                             ls_str_out(cons(substr str 2)ls_str_out)
                             )
                       )
                     
                     (if(setq vnam(cdr(assoc "MESHOBJ" ls_out_parameter)))
                         (progn
                           (setq ls_p(vlax-safearray->list(vlax-variant-value(vla-get-coordinates vnam)))
                                 numy(vla-get-NVertexCount vnam)
                                 ls_rgb(cdr(assoc "TCOLMESH" ls_out_parameter))
                                 ls_p(split_list numy(split_list 3 ls_p))
                                 
                                 str(apply
                                     'strcat
                                     (mapcar
                                      '(lambda(str / strx)
                                         (setq strx
                                               (cond
                                                ((= str "type")"FACEUNION")
                                                ((= str "name")
                                                 (strcat(cdr(assoc "NAME" ls_out_parameter))"-CON"))
                                                ((= str "r")(as-numstr(/(car ls_rgb)255.)))
                                                ((= str "g")(as-numstr(/(cadr ls_rgb)255.)))
                                                ((= str "b")(as-numstr(/(caddr ls_rgb)255.)))
                                                ((= str "properties")
                                                 (strcat
                                                  "\""
                                                  (substr (apply 'strcat
                                                                 (mapcar '(lambda(str)(strcat "|" str))
                                                                         ls_xdata_att))
                                                          2)
                                                  "\"")
                                                 )
                                                (T(setq str ""))
                                                ))
                                         (strcat "," strx))
                                      ls_ifcparameter))

                                 ls_str_out(cons(substr str 2)ls_str_out)
                                 )
                           
                           (setq ii 0 num(1-(length ls_p))
                                 ls_intmesh(inclist 0 numy))

                           (mapcar
                            '(lambda(lst1 lst2 / p01 p02 p03 p04 p11 p12 p13 p14 ls_pmesh jj)
                               ;;(mapcar 'set '(p01 p02 p03 p04)lst1)
                               ;;(mapcar 'set '(p11 p12 p13 p14)lst2)

                               
                               (setq ii(1+ ii)str_p "" i 0 
                                     ls_p_mesh
                                     (mapcar '(lambda(j / p01 p02 p11 p12)
                                                (setq p01(nth(rem j numy)lst1)
                                                      p02(nth(rem(1+ j)numy)lst1)
                                                      p11(nth(rem j numy)lst2)
                                                      p12(nth(rem(1+ j)numy)lst2))
                                                (list p01 p02 p11 p02 p12 p11)
                                                )
                                             ls_intmesh )
                                     ls_p_mesh
                                     (apply 'append(apply 'append ls_p_mesh))
                                     ;;(if(= ii 1)(append p01 p04 p02 p04 p03 p02))
                                     ;;(if(= ii num)(append p14 p11 p13 p11 p12 p13))
                                     
                                     )
                               (mapcar '(lambda(a )
                                          (setq i(1+ i)
                                                str_p(strcat str_p(if(=(rem i 9)1)"|" ",")
                                                             (as-numstr a))
                                                ))
                                       ls_p_mesh)
                               
                               (setq str_p(strcat "\""(substr str_p 2)"\"")
                                     str(apply 'strcat
                                               (mapcar '(lambda(str)
                                                          (if(= str "type")(setq str "FACE")
                                                            (if(= str "face")(setq str str_p)
                                                              (setq str "")))
                                                          (strcat "," str))
                                                       ls_ifcparameter))
                                     ls_str_out(cons(substr str 2) ls_str_out)
                                     )
                               )
                            ls_p(cdr ls_p))
                           
                           (setq str(apply 'strcat
                                           (mapcar '(lambda(str)
                                                      (if(= str "type")(setq str "FACEEND")
                                                        (setq str ""))
                                                      (strcat "," str))
                                                   ls_ifcparameter))
                                 ls_str_out(cons(substr str 2)ls_str_out)
                                 )
                           ))
                     ))
                 
                 )
               
               )
              ((= str_type "CCBOXBLOCK")
               (if(= int_savecsvifc 1)
                   (setq str_out(strcat "CCBOX," str))
                 (setq ls_out_parameter(cons(cons "NAME" str)ls_out_parameter))
                 )
               
               (vlax-for
                obj vnam
                (vla-getXData obj "terraduct3d" 'array_Type 'array_Data )
                (setq ls_xdata
                      (if array_data
                          (split_list 0(mapcar 'vlax-variant-value
                                               (vlax-safearray->list array_data))))
                      str_type(cdr(assoc "terraduct3d" ls_xdata))
                      )

                (setq ls_gcode(entget(vlax-vla-object->ename obj)))
                (cond
                 ((= str_type "CCBOXSOLID")
                  (if(= int_savecsvifc 1)
                      (setq ls_out_parameter
                            (cons(cons "COLCCBOX"(vla-get-color obj))ls_out_parameter))
                    (setq ls_rgb((lambda(vtc)(mapcar '(lambda(a)(a vtc))
                                                     (list vla-get-red vla-get-green vla-get-blue)))
                                 (vla-get-truecolor obj))
                          ))
                  )
                 ((= str_type "CCBOXWIDTH-X")
                  (setq p13(cdr(assoc 13 ls_gcode))p14(cdr(assoc 14 ls_gcode))
                        ls_out_parameter
                        (cons(cons "ZBOTTOM"(caddr p13))ls_out_parameter)
                        ls_out_parameter
                        (cons(cons "DIMSTYLE"(cdr(assoc 3 ls_gcode)))ls_out_parameter)
                        )
                  (if(= int_savecsvifc 1)
                      (setq ls_out_parameter
                            (cons(cons "X0"(car p13))ls_out_parameter)
                            ls_out_parameter
                            (cons(cons "Y0"(cadr p13))ls_out_parameter)
                            ls_out_parameter
                            (cons(cons "X1"(car p14))ls_out_parameter)
                            ls_out_parameter
                            (cons(cons "Y1"(cadr p14))ls_out_parameter)
                            )
                    (setq ls_out_parameter
                          (cons(cons "X0"(* 0.5(+(car p13)(car p14))))ls_out_parameter)
                          ls_out_parameter
                          (cons(cons "rotate"(-(angle(carxy p13)(carxy p14))))ls_out_parameter)
                          ls_out_parameter
                          (cons(cons "dx"(distance p13 p14))ls_out_parameter)
                          )
                    )
                  
                  )
                 ((= str_type "CCBOXHEIGHT")
                  (setq p(cdr(assoc 14 ls_gcode))
                        ls_out_parameter
                        (cons(cons "ZTOP"(caddr p))ls_out_parameter)
                        )
                  )
                 ((= str_type "CCBOXVBACANT")
                  (setq p(cdr(assoc 14 ls_gcode))
                        ls_out_parameter
                        (cons(cons "ZGROUND"(caddr p))ls_out_parameter)
                        )
                  )
                 ((= str_type "CCBOXWIDTH-Y")
                  (setq p(cdr(assoc 13 ls_gcode)))
                  (if(= int_savecsvifc 1)
                      (setq ls_out_parameter
                            (cons(cons "X2"(car p))ls_out_parameter)
                            ls_out_parameter
                            (cons(cons "Y2"(cadr p))ls_out_parameter)
                            )
                    (setq ls_out_parameter
                          (cons(cons "Y0"(* 0.5(+(cadr p)(cadr(cdr(assoc 14 ls_gcode))))))
                               ls_out_parameter)
                          ls_out_parameter
                          (cons(cons "dy"(distance p(cdr(assoc 14 ls_gcode))))ls_out_parameter)
                          )
                    )
                  )
                 
                 ((= str_type "LEVELINGCON")
                  (setq ls_out_parameter
                        (cons(cons "LEVELINGOFFSET"(cdr(assoc "OFFSET" ls_xdata)))
                             ls_out_parameter)
                        ls_out_parameter
                        (cons(cons "LEVELINGHEIGHT"(cdr(assoc "HEIGHT" ls_xdata)))
                             ls_out_parameter)
                        ))
                 
                 
                 ((= str_type "MANHOLE")
                  (setq ls_out_parameter
                        (cons(assoc "CENTER-X" ls_xdata) ls_out_parameter)
                        ls_out_parameter
                        (cons(assoc "CENTER-Y" ls_xdata) ls_out_parameter)
                        ls_out_parameter
                        (cons(cons "MANHOLEHEIGHT"(cdr(assoc "HEIGHT" ls_xdata)))
                             ls_out_parameter)
                        ls_out_parameter
                        (cons(cons "MANHOLERADIUS" (* 0.5(cdr(assoc "DIAM" ls_xdata))))
                             ls_out_parameter)
                        ))
                 
                 )
                
                )
               
               (if(= int_savecsvifc 1)
                   (progn
                     (mapcar
                      '(lambda(lst / str str_initial)
                         (if(setq str(cdr(assoc(car lst)ls_out_parameter)))T
                           (setq str(cadr lst)))
                         (setq str_out(strcat str_out ","(as-numstr str))))
                      (list(list "COLCCBOX")(list "ZBOTTOM")(list "ZTOP")(list "ZGROUND")
                           (list "X0")(list "Y0")(list "X1")(list "Y1")(list "X2")(list "Y2")
                           (list "LEVELINGOFFSET" 0)(list "LEVELINGHEIGHT" 0)
                           (list "CENTER-X" 0)(list "CENTER-Y" 0)
                           (list "MANHOLEHEIGHT" 0)(list "MANHOLERADIUS" 0)
                           (list "DIMSTYLE")
                           )
                      )
                     (setq ls_str_out_ccbox(cons str_out ls_str_out_ccbox)
                           ls_str_out_ccbox
                           (cons(strcat "ATTRIBUTE"
                                        (apply 'strcat
                                               (mapcar '(lambda(str)(strcat "," str))
                                                       ls_xdata_att
                                                       )))
                                ls_str_out_ccbox)
                           )
                     )
                 
                 ((lambda( / vec lst str_name str_r str_g str_b ls_con ang_rot)

                    
                    (setq ls_con(list(cons "name"(cdr(assoc "NAME" ls_out_parameter)))
                                     (cons "r"(as-numstr(/(car ls_rgb)255.)))
                                     (cons "g"(as-numstr(/(cadr ls_rgb)255.)))
                                     (cons "b"(as-numstr(/(caddr ls_rgb)255.)))
                                     (cons "ex" "0")(cons "ey" "0")(cons "ez" "1")
                                     )
                          lst(list
                              
                              (list(cons "type" "SOLIDUNION")
                                   (cons "properties"
                                         (strcat
                                          "\""
                                          (substr (apply 'strcat
                                                         (mapcar '(lambda(str)(strcat "|" str))
                                                                 ls_xdata_att))
                                                  2)
                                          "\"")
                                         )
                                   )
                              
                              (append ls_con
                                      (list(cons "type" "RECT")
                                           (cons "x"(cdr(assoc "X0" ls_out_parameter)))
                                           (cons "y"(cdr(assoc "Y0" ls_out_parameter)))
                                           (cons "z"(cdr(assoc "ZBOTTOM" ls_out_parameter)))
                                           (assoc "rotate" ls_out_parameter)
                                           (assoc "dx" ls_out_parameter)
                                           (assoc "dy" ls_out_parameter)
                                           (cons "height"
                                                 (-(cdr(assoc "ZTOP" ls_out_parameter))
                                                   (cdr(assoc "ZBOTTOM" ls_out_parameter))))
                                           )
                                      )

                              (if(and(setq z(cdr(assoc "LEVELINGHEIGHT" ls_out_parameter)))
                                     (setq w(cdr(assoc "LEVELINGOFFSET" ls_out_parameter))))
                                  (append ls_con
                                          (list(cons "type" "RECT")
                                               (cons "x"(cdr(assoc "X0" ls_out_parameter)))
                                               (cons "y"(cdr(assoc "Y0" ls_out_parameter)))
                                               (cons "z"(-(cdr(assoc "ZBOTTOM" ls_out_parameter))z))
                                               (assoc "rotate" ls_out_parameter)
                                               (cons "dx"(+(cdr(assoc "dx" ls_out_parameter))(* 2 w)))
                                               (cons "dy"(+(cdr(assoc "dy" ls_out_parameter))(* 2 w)))
                                               (cons "height" z)
                                               )
                                          )
                                (progn(setq z 0.)nil)
                                )

                              (if(setq h(cdr(assoc "MANHOLEHEIGHT" ls_out_parameter)))
                                  (append ls_con
                                          (list(cons "type" "CIRCLE")
                                               (cons "x"(cdr(assoc "CENTER-X" ls_out_parameter)))
                                               (cons "y"(cdr(assoc "CENTER-Y" ls_out_parameter)))
                                               (cons "z"(-(cdr(assoc "ZTOP" ls_out_parameter))z))
                                               (cons "height"(cdr(assoc "MANHOLEHEIGHT" ls_out_parameter)))
                                               (cons "radius"(cdr(assoc "MANHOLERADIUS" ls_out_parameter)))
                                               )
                                          )
                                )

                              (list(cons "type" "SOLIDEND") )
                              
                              )
                          
                          lst(vl-remove nil lst)
                          lst(mapcar '(lambda(lst)(vl-remove nil lst))lst)
                          )

                    (mapcar
                     '(lambda(lst)
                        (setq str
                              (apply
                               'strcat
                               (mapcar
                                '(lambda(str / strx)
                                   (if(setq strx(cdr(assoc str lst)))T(setq strx ""))
                                   (strcat ","(as-numstr strx)))
                                ls_ifcparameter )
                               )
                              ls_str_out(cons(substr str 2)ls_str_out)
                              
                              )
                        )
                     lst)
                    
                    ) )
                 )
               
               
               )
              
              ;;--- テンプレートから作った特殊部 / マンホール -------------------
              ;;  ブロックの XDATA にテンプレート名・配置・全パラメータが入っている。
              ;;  CSV はその値をそのまま並べるだけにして、読込時は makeparts を
              ;;  もう一度呼んで作り直す(形状の作り方をここに二重に持たない)。
              ;;  IFC は形状そのものが要るので、テンプレート側の ifcrows に作らせる。
              ((or(= str_type "CCBOXTEMPBLOCK")(= str_type "MANHOLEBLOCK"))
               ((lambda( / bool_mh ls_def ls_val ls_rgbpart int_colpart lst
                           str_part str_temp p_base vecx ls_row num_total num_length)
                  (setq bool_mh(= str_type "MANHOLEBLOCK")
                        ls_def(if bool_mh(td3d_mh_paramdef)(td3d_tmp_paramdef))
                        ;;パラメータは定義の順に引く。項目を足しても列がずれない
                        ls_val(mapcar '(lambda(lst)(cdr(assoc(car lst)ls_xdata)))ls_def)
                        ls_val(if bool_mh(td3d_mh_fill ls_val)(td3d_tmp_fill ls_val))
                        str_temp(cdr(assoc "TEMPLATE" ls_xdata))
                        vecx(list(cdr(assoc "VEC-X" ls_xdata))
                                 (cdr(assoc "VEC-Y" ls_xdata))0.)
                        p_base(if bool_mh
                                  (list(cdr(assoc "CENTER-X" ls_xdata))
                                       (cdr(assoc "CENTER-Y" ls_xdata))
                                       (cdr(assoc "TOPZ" ls_xdata)))
                                (list(cdr(assoc "BASE-X" ls_xdata))
                                     (cdr(assoc "BASE-Y" ls_xdata))
                                     (cdr(assoc "BASE-Z" ls_xdata))))
                        num_total(cdr(assoc "TOTALH" ls_xdata))
                        num_length(cdr(assoc "LENGTH" ls_xdata))
                        ls_rgbpart(list)
                        )
                  ;;この改訂より前に置いたブロックには配置の記録が無い
                  (if(car vecx)T(setq vecx(list 1. 0. 0.)))
                  (if num_total T(setq num_total 0.))
                  (if num_length T(setq num_length 0.))

                  ;;部材ごとの色を集める(マンホールの鉄蓋だけ色が違う)
                  (vlax-for
                   obj vnam
                   (vla-getXData obj "terraduct3d" 'array_Type 'array_Data )
                   (setq lst(if array_data
                                (split_list 0(mapcar 'vlax-variant-value
                                                     (vlax-safearray->list array_data))))
                         str_part(cdr(assoc "PART" lst)))
                   (if(null str_part)T
                     (progn
                       (if(assoc str_part ls_rgbpart)T
                         (setq ls_rgbpart
                               (cons(cons str_part
                                          ((lambda(vtc)
                                             (mapcar '(lambda(a)(a vtc))
                                                     (list vla-get-red vla-get-green
                                                           vla-get-blue)))
                                           (vla-get-truecolor obj)))
                                    ls_rgbpart)))
                       ;;CSV に書く色番号は鉄蓋以外(配置時の int_colccbox)を使う
                       (if(or int_colpart(= str_part "MHCOVER"))T
                         (setq int_colpart(vla-get-color obj)))
                       )))
                  (if int_colpart T(setq int_colpart 8))

                  (cond
                   ;;配置の記録が無いものは作り直せないので飛ばす
                   ((null(car p_base))
                    ;;配置の記録が無いため出力できません。置き直してください
                    (princ(mix_strasc
                           (list "\n" str " : " 37197 32622 12398 35352 37682 12364 28961 12356 12383 12417
                                 20986 21147 12391 12365 12414 12379 12435 12290
                                 32622 12365 30452 12375 12390 12367 12384 12373 12356)))
                    nil)
                   ((= int_savecsvifc 1)
                      ;;--- CSV ---
                      (progn
                        (setq str_out
                              (apply 'strcat
                                     (mapcar '(lambda(a)(strcat ","(as-numstr a)))
                                             (append
                                              (list str int_colpart str_temp
                                                    (cdr(assoc "PROJECT-D" ls_xdata))
                                                    (cdr(assoc "PROJECT-H" ls_xdata)))
                                              (if bool_mh
                                                  (list(car p_base)(cadr p_base)
                                                       (caddr p_base)num_total)
                                                (list num_length
                                                     (car p_base)(cadr p_base)
                                                     (caddr p_base)))
                                              (list(car vecx)(cadr vecx))
                                              ls_val)))
                              str_out(strcat(if bool_mh "MANHOLETEMP" "CCBOXTEMP")str_out)
                              ls_str_out_temp(cons str_out ls_str_out_temp)
                              ls_str_out_temp
                              (cons(strcat "ATTRIBUTE"
                                           (apply 'strcat
                                                  (mapcar '(lambda(str)(strcat "," str))
                                                          ls_xdata_att)))
                                   ls_str_out_temp)
                              )
                        ))

                   ;;--- IFC ---
                   ;;  部材を SOLIDUNION 〜 SOLIDEND で囲んで 1 オブジェクトにする。
                   ;;  押し出し系(RECT/CIRCLE/CYLINDER)と FACE が混ざるときは
                   ;;  ifc_exchange.py 側が RepresentationType を Brep にする。
                   (T
                      (setq ls_row
                            (if bool_mh
                                ;;TOTALH が 0 のときはテンプレートの合計高さを使う
                                (td3d_mh_ifcrows ls_val p_base vecx
                                                 (if(< num_total 1e-8)nil num_total))
                              (td3d_tmp_ifcrows ls_val p_base vecx num_length))
                            ls_row
                            (cons(list(cons "type" "SOLIDUNION")
                                      (cons "name" str)
                                      (cons "properties"
                                            (strcat
                                             "\""
                                             (substr
                                              (apply 'strcat
                                                     (mapcar '(lambda(str)(strcat "|" str))
                                                             ls_xdata_att))
                                              2)
                                             "\"")))
                                 ;;部材ごとの色を足す
                                 (append
                                  (mapcar
                                   '(lambda(lst / ls_rgb)
                                      (setq ls_rgb(cdr(assoc(cdr(assoc "part" lst))
                                                            ls_rgbpart)))
                                      (if ls_rgb T(setq ls_rgb(list 128 128 128)))
                                      (append
                                       (list(cons "name" str)
                                            (cons "r"(/(car ls_rgb)255.))
                                            (cons "g"(/(cadr ls_rgb)255.))
                                            (cons "b"(/(caddr ls_rgb)255.)))
                                       lst))
                                   ls_row)
                                  (list(list(cons "type" "SOLIDEND"))))))

                      (mapcar
                       '(lambda(lst)
                          (setq str_out
                                (apply
                                 'strcat
                                 (mapcar
                                  '(lambda(str / strx)
                                     (if(setq strx(cdr(assoc str lst)))T(setq strx ""))
                                     (strcat ","(as-numstr strx)))
                                  ls_ifcparameter))
                                ls_str_out(cons(substr str_out 2)ls_str_out)))
                       ls_row)
                      ))
                  ))
               )

              ((and(= str_type "PROJECT")(= int_savecsvifc 1))
               (setq ls_p_ceircle(list)ls_p_text(list))
               (vlax-for
                obj vnam

                (cond
                 ((=(vla-get-ObjectName obj)"AcDb3dPolyline")
                  (setq ls_p(split_list 3(vlax-safearray->list(vlax-variant-value(vla-get-coordinates obj))))
                        int_col(vla-get-color obj)
                        hand_road(vla-get-handle obj)
                        )
                  )
                 ((=(vla-get-ObjectName obj)"AcDbCircle")
                  (setq ls_p_center
                        (cons(vlax-safearray->list(vlax-variant-value(vla-get-center obj)))
                             ls_p_center))
                  )
                 ((=(vla-get-ObjectName obj)"AcDbText")
                  (setq ls_p_text
                        (cons(cons
                              (vla-get-rotation obj)
                              (vlax-safearray->list(vlax-variant-value(vla-get-TextAlignmentPoint obj)))
                              )
                             ls_p_text))
                  )
                 
                 )
                )
               
               (setq ls_str_out(cons(strcat "PROJECTROAD," str "," (as-numstr int_col)"," hand_road)
                                    ls_str_out)
                     ls_str_out
                     (cons(strcat "ATTRIBUTE"
                                  (apply 'strcat
                                         (mapcar '(lambda(str)(strcat "," str))
                                                 ls_xdata_att
                                                 )))
                          ls_str_out)
                     )

               
               (mapcar
                '(lambda(p / str_i str)
                   (setq str_i
                         (if(apply 'or(mapcar '(lambda(pc)(<(distance p pc)1e-8))ls_p_center))
                             "1" "0")
                         str(apply 'strcat(mapcar '(lambda(a)(strcat ","(as-numstr a)))p))
                         )
                   (if ls_p_text
                       (progn
                         (mapcar '(lambda(a)(setq str(strcat str ","(as-numstr a))))
                                 (car ls_p_text))
                         (setq ls_p_text(cdr ls_p_text))
                         ))
                   (setq str(strcat "POINT," str_i str)
                         ls_str_out(cons str ls_str_out)
                         )
                   )
                ls_p)
               
               (setq ls_str_out(cons(strcat "PROJECTROADEND")ls_str_out))
               
               )
              )
             
             )
          ls_vnam_select )
         
         ;;ls_str_out
         
         (if(= int_savecsvifc 1)
             (setq ls_str_out(append ls_str_out_temp ls_str_out_ccbox
                                     ls_str_out_duct ls_str_out)))
         
         (setq bool_ifcexe nil)
         (if(setq str_path
                  (if(= int_savecsvifc 1);;CSV保存
                      (getfiled(mix_strasc(list "CSV" 20445 23384))
                               (strcat(getvar "DWGPREFIX")"csvoutput")"csv" 1)
                    (if(= int_savecsvifc 3);;IFC保存
                        (getfiled(mix_strasc(list "IFC" 20445 23384))
                                 (strcat(getvar "DWGPREFIX")"ifcoutput")"ifc" 1)
                      )
                    )
                  )
             
             (progn
               (if(= int_savecsvifc 3)
                   (setq str_pathifc str_path
                         ;; cpath_terraduct3d(strcat (getenv "APPDATA")"\\" "terraduct3d-ac" "\\app")
                         str_path(strcat cpath_terraduct3d "\\pyexe\\csv_to_ifc.csv")))
               
               (if command_for_alter
                   (setq open_file (open str_path "w" ) );;"utf8"
                 (progn
                   (setq open_file (open str_path "w" "utf8") )
                   (write-char 65279 open_file) ;; BOM
                   ))

               
               (if open_file
                   (progn
                     (mapcar '(lambda(str)(write-line str open_file))(reverse ls_str_out))
                     (close open_file)
                     
                     (if(= int_savecsvifc 1)
                         (x-alert(list 20986 21147 12375 12414 12375 12383))
                       (setq bool_ifcexe T) )
                     
                     )
                 (progn
                   
                   (x-alert(list 12501 12449 12452 12523 12364 38283 12363 12428 12390 12356 12427 12383 12417 26360 36796 12415 12391 12365 12414 12379 12435 12391 12375 12383 ))
                   
                   )
                 )
               
               )
           (x-alert(list 12501 12449 12452 12523 12364 36984 25246 12373 12428 12414 12379 12435 12391 12375 12383 ))
           )
         
         
         (if(and(= int_savecsvifc 3) str_path bool_ifcexe)
             (progn
               ;; (setq cpath_terraduct3d(strcat (getenv "APPDATA")"\\" "terraduct3d-ac" "\\app"))
               
               (setq str_input str_path str_data str_pathifc
                     str_path(strcat cpath_terraduct3d "\\pyexe\\main.exe")
                     bool_loop T size_file nil
                     int_time 100 ms_loop nil ms_max 20000 
                     )
               
               ;; (setq str_lasfile str_laspath )
               
               ;;(if(findfile str_data)(vl-file-delete str_data))
               (setq str_errlog(strcat cpath_terraduct3d "\\pyexe\\ifc_error.log"))
               (if(findfile str_data)(vl-file-delete str_data))
               (if(findfile str_errlog)(vl-file-delete str_errlog))
               
               (setq wsh (vlax-create-object "WScript.Shell"))
               (setq cmd(strcat "\"" str_path "\" "
                                "\"" "ifc"    "\" "
                                "\"" str_input "\" "
                                "\"" str_data "\"" ))
               (vlax-invoke-method wsh 'Run cmd 0 :vlax-true)
               (vlax-release-object wsh)
               
               (setq ms_loop(getvar "MILLISECS"))
               (while bool_loop
                 (setq ms_start(getvar "MILLISECS"))
                 (if(>(- ms_start ms_loop)ms_max)(setq bool_loop nil))
                 (while(<(-(getvar "MILLISECS")ms_start)int_time) )
                 (if(findfile str_data)
                     (if(= size_file(vl-file-size str_data))(setq bool_loop nil)
                       (setq size_file(vl-file-size str_data)) ))
                 )

               (if(findfile str_data)
                   (x-alert(list "IFC" 12434 20986 21147 12375 12414 12375 12383))   ;;出力しました
                 ((lambda( / file_r str str_msg)
                    (setq str_msg "")
                    (if(setq file_r(open str_errlog "r"))
                        (progn
                          (while(setq str(read-line file_r))
                            (setq str_msg(strcat str_msg "\n" str)))
                          (close file_r)))
                    (x-alert(list 22833 25943 12375 12414 12375 12383 "\n" str_msg))
                    ))
                 )
               
               ;; (if(findfile str_data)
               ;;     ;;IFCを出力しました
               ;;     ;;pythonメッセージ消す
               ;;     (x-alert(mix_strasc(list "\nIFC" 12434 20986 21147 12375 12414 12375 12383 )))
               ;;   (x-alert(list 22833 25943 12375 12414 12375 12383))
               ;;   )
               
               ))
         

         (mapcar '(lambda(v)(vla-Highlight v :vlax-false))ls_vnam_select)
         (setq ls_vnam_select nil ls_vnam_highlight nil)
         
         
         )
        
        ((if(= int_savecsvifc 2);;CSV読込
             (setq str_path
                   (getfiled(mix_strasc(list "CSV" 35501 36796))
                            (strcat(getvar "DWGPREFIX")"csvoutput")"csv" 0))
           (progn
             (x-alert(list 12501 12449 12452 12523 12364 36984 25246 12373 12428 12414 12379 12435 12391 12375 12383 ))
             nil
             ) )
         
         (setq open_file (open str_path "r")
               ls_str_in(list))
         
         (while(setq str(read-line open_file))
           (setq ls_str_in(cons(getlist_str_split str ",")ls_str_in))
           )
         (close open_file)

         (setq ls_hand_road(list)
               ls_str_in(reverse ls_str_in)
               int_objtype nil
               ls_read_duct(list)
               ls_read_ccbox(list)
               ls_read_projectroad(list)
               ls_existblock(list)
               )
         
         ;;(setq radius_node(if(= pitch_project 0.)0.05 pitch_project))
         (if(if pitch_mesh(>(abs pitch_mesh)1e-8))T(setq pitch_mesh 0.5))
         (while ls_str_in
           (setq lst(car ls_str_in)ls_str_in(cdr ls_str_in)
                 str(car lst)ls_vnam_copy (list))
           
           (cond
            ((or(= str "DUCTBLOCK")(= str "CCBOX")(= str "PROJECTROAD")
                (= str "CCBOXTEMP")(= str "MANHOLETEMP"))
             (setq str_name(cadr lst)))
            ;; (
            ;;  (setq i 0)
            ;;  (while(progn
            ;;          (setq str_name(strcat "PROJECTROAD_READ" "$"(itoa(setq i(1+ i)))))
            ;;          (null(vl-catch-all-error-p
            ;;                (vl-catch-all-apply 'vla-Item(list vnam_blocktable str_name))))
            ;;          )
            ;;    )
            ;;  )
            (T(setq str_name nil))
            
            )
           
           (if(if str_name
                  (if(vl-catch-all-error-p
                      (setq block(vl-catch-all-apply 'vla-Item(list vnam_blocktable str_name))))
                      (setq block(vla-Add vnam_blockTable(vlax-3d-point 0 0 0)str_name) )
                    (progn
                      
                      (setq ls_existblock(cons str_name ls_existblock))
                      (if(= int_overwrite_readcsv 0)
                          (progn
                            (setq ls_vla-release(cons block ls_vla-release))
                            nil)
                        
                        (progn
                          (if(setq set_ent(ssget "X"(list(cons 2 str_name))))
                              (progn
                                (setq num(sslength set_ent))
                                (while(>(setq num(1- num))-1)
                                  (setq vnam(vlax-ename->vla-object(ssname set_ent num)))
                                  (vla-delete vnam)
                                  )
                                ))
                          (vla-delete block)
                          
                          (mapcar '(lambda(v)
                                     (vlax-release-object v)
                                     (setq ls_vla-release(vl-remove v ls_vla-release))
                                     )
                                  (list block))
                          (setq block(vla-Add vnam_blockTable(vlax-3d-point 0 0 0)str_name))
                          T
                          )
                        ))
                    ) )
               (progn
                 (setq ls_xdata_att nil)
                 (cond
                  ((= str "DUCTBLOCK")
                   
                   (mapcar '(lambda(lst val / sym str_type)
                              (setq sym(car lst)str_type(cadr lst))
                              (if(= str_type "REAL")(setq val(atof val))
                                (if(= str_type "INT")(setq val(atoi val))))
                              (set sym val)
                              )
                           (list(list 'str_name)
                                (list 'int_colduct_temp "INT")
                                (list 'int_colprotect_temp "INT")
                                (list 'diam_duct_temp "REAL")
                                (list 'int_protectcon_temp "INT")
                                (list 'width_protect_temp "REAL")
                                (list 'height_protect_temp "REAL")
                                (list 'filet_protect_temp "REAL")
                                )
                           (cdr lst))

                   (setq pitch_mesh(min pitch_project diam_duct_temp))
                   (if(<(abs pitch_mesh)1e-8)
                       (setq pitch_mesh diam_duct_temp))
                   
                   
                   (if(=(caar ls_str_in)"ATTRIBUTE")
                       (setq ls_xdata_att(cdar ls_str_in)
                             ls_str_in(cdr ls_str_in)))
                   
                   (setq int_duct -1 int_depth 0 ls_pmesh(list)ls_pbar(list)
                         p_arcend nil )
                   (while(progn(setq lst(car ls_str_in) str_type(car lst))
                               (if(= str_type "DUCTBLOCKEND")
                                   (progn(setq ls_str_in(cdr ls_str_in))
                                         nil)
                                 T) )
                     
                     (cond
                      ((= str_type "DEPTH")
                       (setq int_duct(1+ int_duct)
                             ls_dim
                             (mapcar
                              '(lambda(lst i / p0 p1)
                                 (setq lst(cdr lst)
                                       p0(mapcar 'atof(list(car lst)(cadr lst)(caddr lst)))
                                       lst(cdddr lst)
                                       p1(mapcar 'atof(list(car lst)(cadr lst)(caddr lst)))
                                       lst(cdddr lst)
                                       str_dim_temp(car lst)
                                       hand_road(cdr(assoc(cadr lst)ls_hand_road))
                                       )
                                 
                                 (list p0 p1(if hand_road hand_road(setq hand_road "")))
                                 )
                              ls_str_in (list 0 1)
                              )
                             ls_str_in(cddr ls_str_in)
                             p_line0(cadar ls_dim)p_line1(cadadr ls_dim)
                             vec_line(unit_vector(carxyz(mapcar '- p_line0 p_line1)0))
                             )

                       (mapcar
                        '(lambda(lst ii / p0 p1 h)
                           (setq p0(car lst)p1(cadr lst)h(caddr lst)
                                 str_level(depth_level_str p0 p1)
                                 entna(make_2pdimension
                                       nil(list p0 p1 vec_line
                                                (apply '+(mapcar '* vec_line p0))
                                                nil(* 0.5 pi)
                                                0. str_level
                                                (if(vl-position str_dim_temp ls_dimstyle)
                                                    str_dim_temp str_dimstyle_ductlevel)
                                                )
                                       )
                                 vnam(vlax-ename->vla-object entna)
                                 ls_vnam_copy(cons vnam ls_vnam_copy)
                                 )
                           (vla-put-Arrowhead1Type vnam 13)
                           (vla-put-Arrowhead2Type vnam 6)
                           (vla-put-ExtLine1Suppress vnam -1)
                           (vla-put-ExtLine2Suppress vnam -1)
                           (vla-put-HorizontalTextPosition vnam 3)
                           (if(= int_invisible_annotation 1)(vla-put-visible vnam :vlax-false))
                           (vla-put-color vnam int_colductdim)
                           (set_xda vnam(list(cons 1000 "DEPTH")
                                             (cons 1000 "NUM")(cons 1071 int_duct)
                                             (cons 1000 "SIDE")(cons 1071 ii)
                                             (cons 1000 "ROAD")(cons 1000 h)
                                             )
                                    "terraduct3d")
                           )
                        ls_dim (list 0 1))
                       
                       (setq vnam
                             (vla-addline
                              (vla-get-modelspace(vla-get-activedocument(vlax-get-acad-object)))
                              (vlax-3d-point p_line0)(vlax-3d-point p_line1))
                             ls_vnam_copy(cons vnam ls_vnam_copy)
                             )
                       
                       (vla-put-color vnam int_colductdim)
                       (set_xda vnam(list(cons 1000 "LINE")
                                         (cons 1000 "NUM")(cons 1071 int_duct))
                                "terraduct3d")

                       
                       )
                      ((= str_type "ARC")
                       
                       (mapcar
                        '(lambda(lst ii / )
                           (setq lst(cdr lst)
                                 p15(mapcar 'atof(list(car lst)(cadr lst)(caddr lst)))
                                 lst(cdddr lst)
                                 p13(mapcar 'atof(list(car lst)(cadr lst)(caddr lst)))
                                 lst(cdddr lst)
                                 p14(mapcar 'atof(list(car lst)(cadr lst)(caddr lst)))
                                 lst(cdddr lst)
                                 p16(mapcar 'atof(list(car lst)(cadr lst)(caddr lst)))
                                 lst(cdddr lst)
                                 dist_normal(atof(caddr lst)) lst(cdddr lst)
                                 vec_normal(mapcar 'atof(list(car lst)(cadr lst)(caddr lst)))
                                 dist_normal(apply '+(mapcar '* p15 vec_normal))
                                 lst(cdddr lst)
                                 str_dim_temp(car lst)
                                 
                                 rr(distance p15 p13)
                                 entna(make_arcdimension
                                       nil(list p15 p13 p14 p16 rr
                                                vec_normal dist_normal
                                                (strcat "R="(if(< rr 1e-8)(chr 8734)
                                                              (rtos rr 2 3 )))
                                                (if(vl-position str_dim_temp ls_dimstyle)
                                                    str_dim_temp str_dimstyle_ductlevel)
                                                ))
                                 vnam(vlax-ename->vla-object entna)
                                 ls_vnam_copy(cons vnam ls_vnam_copy)
                                 )
                           (if(= int_invisible_annotation 1)(vla-put-visible vnam :vlax-false))
                           (vla-put-color vnam int_colductdim)
                           (arc2_dimstyle vnam)
                           
                           (setq p_arcend p14)
                           (set_xda vnam(list(cons 1000 "ARC")
                                             (cons 1000 "NUM")(cons 1071 int_duct)
                                             (cons 1000 "SIDE")(cons 1071 ii)
                                             (cons 1000 "RADIUS")(cons 1040 rr)
                                             )
                                    "terraduct3d")

                           (if(<(distance p13 p14)1e-8) T
                             (progn
                               (setq vec13(mapcar '- p13 p15)
                                     vec14(mapcar '- p14 p15)
                                     vec13(mapcar '(lambda(a)(/ a rr))vec13)
                                     vec14(mapcar '(lambda(a)(/ a rr))vec14)
                                     vec0(cross_product vec_normal vec13)
                                     vec1(cross_product vec_normal vec14)
                                     )

                               (setq p(if ls_pbar(caar ls_pbar)p_line0))
                               
                               (if(<(apply '+(mapcar '* vec0 vec14))0)(setq vec0(mapcar '- vec0)))
                               (if(>(apply '+(mapcar '* vec1 vec13))0)(setq vec1(mapcar '- vec1)))
                               (if(<(apply '+(mapcar '*(mapcar '- p13 p)vec0))-1e-8)
                                   (setq ls_pbar(cons(list p13 nil vec0)(cdr ls_pbar)))
                                 ;; (if(= int_protectcon_temp 2)T
                                 ((lambda(p / d n i dd pm)
                                    (if ls_pbar T(setq ls_pbar(cons(list p_line0 nil vec0)(cdr ls_pbar))))
                                    (setq d(distance p p13) n(1+(fix(/ d pitch_mesh))) d(/ d n)
                                          dd(- d))
                                    (while(>(setq n(1- n))-1)
                                      (setq dd(+ dd d)
                                            pm(mapcar '(lambda(a b)(+ a(* dd b)))p vec0)
                                            ls_pmesh(cons(list pm vec0)ls_pmesh)
                                            )
                                      )
                                    )
                                  p)
                                 ;; )
                                 )

                               (if(<(distance(caar ls_pbar)p13)1e-8)(setq ls_pbar(cdr ls_pbar)))
                               (setq ls_pbar(cons(list p13 p15 vec0)ls_pbar)
                                     ls_pbar(cons(list p14 nil vec1)ls_pbar)
                                     )
                               
                               ((lambda( / d n i ang vec_x vec_y pm dd c s v)
                                  (setq ang(atan(distance(cross_product vec13 vec14)(list 0 0 0))
                                                (apply '+(mapcar '* vec13 vec14)))
                                        vec_x(mapcar '(lambda(a)(* a rr))vec13)
                                        vec_y(mapcar '(lambda(a)(* a rr))vec0)
                                        d(* rr ang) n(1+(fix(/ d(min(* 0.5 rr) pitch_mesh) )))
                                        d(/ ang n)
                                        ang(- d))
                                  
                                  (while(>(setq n(1- n))-1)
                                    (setq ang(+ ang d)c(cos ang)s(sin ang)
                                          v(mapcar '(lambda(x y)(+ (* -1 s x)(* c y)))vec13 vec0)
                                          pm(mapcar '(lambda(a x y)(+ a(* c x)(* s y)))p15 vec_x vec_y)
                                          ls_pmesh(cons(list pm v)ls_pmesh)
                                          )
                                    )
                                  ))
                               
                               ))
                           )
                        ls_str_in
                        (list 0 1))
                       (setq ls_str_in(cddr ls_str_in))
                       
                       )
                      (T(setq ls_str_in(cdr ls_str_in)))
                      )

                     
                     )
                   
                   (if p_arcend T(setq p_arcend p_line0))
                   (setq ls_pbar(cons(list p_line1 nil vec_line) ls_pbar))

                   (setq vec0(unit_vector(mapcar '- p_line1 p_arcend)))
                   (if(<(apply '+(mapcar '*(mapcar '- p_line1 p_arcend)vec0))-1e-8)
                       (setq ls_pmesh(cons(list p_arcend vec0)ls_pmesh) )
                     ((lambda(p / d n i dd pm)
                        (setq d(distance p p_line1) n(1+(fix(/ d pitch_mesh))) d(/ d n)
                              dd(- d))
                        (while(>(setq n(1- n))-1)
                          (setq dd(+ dd d)
                                pm(mapcar '(lambda(a b)(+ a(* dd b)))p vec0)
                                ls_pmesh(cons(list pm vec0)ls_pmesh)
                                )
                          )
                        (setq ls_pmesh(cons(list p_line1 vec0)ls_pmesh))
                        
                        )
                      p_arcend)
                     ;; )
                     )

                   
                   (setq ls_pcenterline(mapcar 'car(reverse ls_pmesh)))

                   (if(= int_ductsolidmesh 1)
                       (progn
                         (setq ls_pbar(reverse ls_pbar)
                               entna(bendpipe_lwpsld
                                     (* 0.5 diam_duct_temp) ls_pbar (getvar "CLAYER") nil)
                               vnam(vlax-ename->vla-object entna)
                               )
                         )
                     (progn
                       (setq numy 32
                             ls_intmesh(inclist 0 numy)
                             ang_d(/(* 2. pi)numy)
                             r(* 0.5 diam_duct_temp)
                             vecxp nil vecyp nil
                             )
                       
                       (setq ls_pduct
                             (mapcar
                              '(lambda(lst / p v vecx vecy)
                                 (setq p(car lst)v(cadr lst)
                                       v(unit_vector v)
                                       vecx(trans-x(list 1 0 0)v(list 0 0 1))
                                       vecy(trans-x(list 0 1 0)v(list 0 0 1))
                                       )

                                 (if(if vecxp(>(apply '+(mapcar '* vecx vecxp))0)T)T
                                   (setq vecx vecxp))
                                 (setq vecxp vecx)
                                 (if(<(caddr vecy)0)(setq vecy(mapcar '- vecy)))
                                 (mapcar '(lambda(i / c s)
                                            (setq c(cos(* ang_d i))s(sin(* ang_d i)))
                                            (mapcar '(lambda(a x y)(+(* r c x)(* r s y)a))
                                                    p vecx vecy))
                                         ls_intmesh)
                                 )
                              (reverse ls_pmesh)
                              )
                             
                             numx(length ls_pduct)
                             ls_p(apply 'append(apply 'append ls_pduct))
                             )
                       
                       (setq array_mesh(vlax-make-safearray vlax-vbDouble(cons 0(1-(length ls_p)))))
                       (vlax-safearray-fill array_mesh ls_p)
                       (setq vnam
                             (vla-Add3DMesh
                              (vla-get-ModelSpace(vla-get-ActiveDocument (vlax-get-acad-object)))
                              numx numy array_mesh)
                             
                             )
                       (vla-put-nclose vnam :vlax-true)
                       )
                     )
                   
                   (vla-put-color vnam int_colduct_temp)
                   (setq ls_vnam_copy(cons vnam ls_vnam_copy))
                   (vla-put-visible vnam :vlax-true)
                   
                   
                   (set_xda vnam(list(cons 1000 "DUCTSOLID")
                                     (cons 1000 "DIAM")(cons 1040 diam_duct_temp)
                                     )
                            "terraduct3d")
                   
                   (setq ls_p(apply 'append ls_pcenterline)
                         array_p(vlax-make-safearray vlax-vbDouble(cons 0(1-(length ls_p)))))
                   (vlax-safearray-fill array_p ls_p)
                   (setq vnam(vla-Add3dPoly
                              (vla-get-ModelSpace(vla-get-ActiveDocument(vlax-get-acad-object)))
                              array_p))
                   (setq ls_vnam_copy(cons vnam ls_vnam_copy))
                   (set_xda vnam(list(cons 1000 "CENTERLINE"))"terraduct3d")

                   
                   (if(setq numy(if(= int_protectcon_temp 0)
                                    (if(= filet_protect_temp 0.)4 8)
                                  (if(= int_protectcon_temp 1)
                                      (if(= filet_protect_temp 0.)-4 -6)
                                    )))
                       (progn
                         (setq int_corner numy
                               
                               w(* 0.5 width_protect_temp)
                               h(* 0.5 height_protect_temp)
                               f filet_protect_temp
                               
                               ls_pmesh
                               (mapcar
                                '(lambda(lst / p v vecx vecy)
                                   (setq p(car lst)v(cadr lst)
                                         v(unit_vector(carxyz v 0.))
                                         vecx(trans-x(list 1 0 0)v(list 0 0 1))
                                         vecy(trans-x(list 0 1 0)v(list 0 0 1))
                                         )
                                   
                                   (vl-remove
                                    nil
                                    (mapcar '(lambda(lst / bool iw iwf ih ihf)
                                               (mapcar 'set '(bool iw iwf ih ihf)lst)
                                               (if(vl-position numy bool)
                                                   (mapcar '(lambda(a x y)(+(*(+(* iw w)(* iwf f))x)
                                                                            (*(+(* ih h)(* ihf f))y) a))
                                                           p vecx vecy))
                                               )
                                            (list(list(list 8 4)-1  1 1 0)
                                                 (list(list 8)  -1  0 1 -1)
                                                 (list(list -6 -4)-1 0 0 0)
                                                 (list(list 8 4 -6 -4)-1 0 -1 1)
                                                 (list(list 8 -6)-1  1 -1 0)
                                                 (list(list 8 -6) 1 -1 -1 0)
                                                 (list(list 8 4 -6 -4) 1 0 -1 1)
                                                 (list(list -6 -4) 1 0 0 0)
                                                 (list(list 8)   1  0 1 -1)
                                                 (list(list 8 4) 1 -1 1 0)
                                                 ))
                                    )
                                   )
                                (reverse ls_pmesh)
                                )
                               
                               numx(length ls_pmesh)
                               numy(abs numy)
                               ls_p(apply 'append(apply 'append ls_pmesh))
                               )
                         
                         (setq array_mesh(vlax-make-safearray vlax-vbDouble(cons 0(1-(length ls_p)))))
                         (vlax-safearray-fill array_mesh ls_p)
                         (setq vnam
                               (vla-Add3DMesh
                                (vla-get-ModelSpace(vla-get-ActiveDocument (vlax-get-acad-object)))
                                numx numy array_mesh)

                               )
                         
                         (vla-put-layer vnam str_layprotect)
                         (vla-put-color vnam int_colprotect)
                         (vla-put-nclose vnam :vlax-true)

                         (setq ls_vnam_copy(cons vnam ls_vnam_copy))
                         (set_xda vnam(list(cons 1000 "CONMESH")
                                           (cons 1000 "CORNER")(cons 1071 int_corner)
                                           (cons 1000 "WIDTH")(cons 1040 width_protect_temp)
                                           (cons 1000 "HEIGHT")(cons 1040 height_protect_temp)
                                           ;;FILET に height を書いていた書き損じを修正
                                           (cons 1000 "FILET")(cons 1040 filet_protect_temp)
                                           )
                                  "terraduct3d")
                         ))
                   
                   (setq ls_xdata(list(cons 1000 "DUCTBLOCK")))
                   
                   )
                  ((= str "CCBOX")

                   (mapcar '(lambda(lst val / sym str_type)
                              (setq sym(car lst)str_type(cadr lst))
                              (if(= str_type "REAL")(setq val(atof val))
                                (if(= str_type "INT")(setq val(atoi val))))
                              (set sym val)
                              )
                           (list(list 'str_name)
                                (list 'int_colccbox_temp "INT")
                                (list 'z_bottom "REAL")
                                (list 'z_top "REAL")
                                (list 'z_ground "REAL")
                                (list 'x0 "REAL") (list 'y0 "REAL")
                                (list 'x1 "REAL") (list 'y1 "REAL")
                                (list 'x2 "REAL") (list 'y2 "REAL")
                                (list 'offset_levelingcon_temp "REAL")
                                (list 'height_levelingcon_temp "REAL")
                                (list 'xc "REAL") (list 'yc "REAL")
                                (list 'height_manhole_temp "REAL")
                                (list 'radius_manhole_temp "REAL")
                                (list 'str_dim_temp)
                                )
                           (cdr lst))

                   (if(=(caar ls_str_in)"ATTRIBUTE")
                       (setq ls_xdata_att(cdar ls_str_in)
                             ls_str_in(cdr ls_str_in)))
                   
                   (setq vecx(list(- x1 x0)(- y1 y0)0)
                         distx(distance(list x0 y0)(list x1 y1))
                         vecx(mapcar '(lambda(a)(/ a distx))vecx)
                         vecy(list(- x2 x0)(- y2 y0)0)
                         disty(distance(list x0 y0)(list x2 y2))
                         vecy(mapcar '(lambda(a)(/ a disty))vecy)
                         p_ccbox0(mapcar '(lambda(a x y)(+(* x distx 0.5)(* y disty 0.5)a))
                                         (list x0 y0 z_bottom)vecx vecy)
                         
                         entna(rac_sld(* 0.5 distx)(* 0.5 disty)(- z_top z_bottom)
                                      p_ccbox0 0(list 0 0 1)vecx(getvar "CLAYER")nil)
                         vnam(vlax-ename->vla-object entna)
                         ls_vnam_copy(cons vnam ls_vnam_copy)
                         )
                   (set_xda vnam(list(cons 1000 "CCBOXSOLID") ) "terraduct3d")
                   (vla-put-color vnam int_colccbox_temp)
                   
                   (setq vec_normal(list(-(car vecy))(-(cadr vecy))0)
                         p0(mapcar '(lambda(a x y)(+ a(* -0.5 distx x)(* -0.5 disty y)))
                                   p_ccbox0 vecx vecy)
                         dist_normal(apply '+(mapcar '* p0 vec_normal))
                         )
                   
                   (mapcar
                    '(lambda(lst / p0 p1 vec_normal dist_normal vecy ang hh str_xdata)
                       (mapcar 'set '(p0 p1 vec_normal dist_normal vecy ang hh str_xdata)lst)
                       (setq entna(make_2pdimension
                                   nil(list p0 p1 vec_normal dist_normal vecy ang hh
                                            ""
                                            (if(vl-position str_dim_temp ls_dimstyle)
                                                str_dim_temp str_dimstyle_ductlevel)
                                            ))
                             vnam(vlax-ename->vla-object entna)
                             ls_vnam_copy(cons vnam ls_vnam_copy)
                             )
                       (vla-put-Arrowhead1Type vnam 13)
                       (vla-put-Arrowhead2Type vnam 6)

                       
                       (set_xda vnam(list(cons 1000 str_xdata) )
                                "terraduct3d")
                       )
                    (list(list p0 (mapcar '(lambda(a b)(+ a(* b distx)))p0 vecx)
                               vec_normal dist_normal(list 0 0 1)0.(* 0.2(- z_top z_bottom))
                               "CCBOXWIDTH-X")
                         (list p0 (mapcar '+ p0(list 0 0(- z_top z_bottom)))
                               vec_normal dist_normal(mapcar '- vecx)(* 0.5 pi)
                               (* 0.2(- z_top z_bottom))
                               "CCBOXHEIGHT")
                         (list(mapcar '+ p0(list 0 0(- z_top z_bottom)))
                              (carxyz p0 z_ground)
                              vec_normal dist_normal(mapcar '- vecx)(* 0.5 pi)
                              (* 0.2(- z_top z_bottom))
                              "CCBOXVBACANT")
                         (list(mapcar '(lambda(a b)(+ a(* -1 b disty))) p0 vec_normal)
                              p0 (mapcar '- vecx)(-(apply '+(mapcar '* vecx p0)))
                              (list 0 0 1)0.(* 0.2(- z_top z_bottom))
                              "CCBOXWIDTH-Y")
                         )
                    )

                   (if(< height_levelingcon_temp 1e-8)T
                     (progn
                       (setq entna(rac_sld(+(* 0.5 distx)offset_levelingcon_temp)
                                          (+(* 0.5 disty)offset_levelingcon_temp)
                                          height_levelingcon_temp
                                          (carxyz p_ccbox0(- z_bottom height_levelingcon_temp))
                                          0(list 0 0 1)vecx(getvar "CLAYER")nil)
                             vnam(vlax-ename->vla-object entna)
                             ls_vnam_copy(cons vnam ls_vnam_copy)
                             )
                       
                       (set_xda vnam(list(cons 1000 "LEVELINGCON")
                                         (cons 1000 "OFFSET")(cons 1040 offset_levelingcon_temp)
                                         (cons 1000 "HEIGHT")(cons 1040 height_levelingcon_temp)
                                         )
                                "terraduct3d")
                       (vla-put-color vnam int_colccbox_temp)
                       
                       ))
                   
                   (if(or(= radius_manhole_temp 0.)(= height_manhole_temp 0.))T
                     (progn
                       (setq entna(pole_sld radius_manhole_temp
                                            height_manhole_temp
                                            (list xc yc z_top)
                                            (list 0 0 1)(getvar "CLAYER")nil)
                             vnam(vlax-ename->vla-object entna)
                             ls_vnam_copy(cons vnam ls_vnam_copy)
                             )
                       
                       (set_xda vnam(list(cons 1000 "MANHOLE")
                                         (cons 1000 "CENTER-X")(cons 1040(car p_manhole))
                                         (cons 1000 "CENTER-Y")(cons 1040(cadr p_manhole))
                                         (cons 1000 "DIAM")(cons 1040(* 2. radius_manhole_temp))
                                         (cons 1000 "HEIGHT")(cons 1040 height_ccboxtop_temp)
                                         )
                                "terraduct3d")
                       (vla-put-color vnam int_colccbox_temp)
                       
                       ))

                   (setq ls_xdata(list(cons 1000 "CCBOXBLOCK")
                                      (cons 1000 "PROJECT-D")(cons 1000(if str_lasground str_lasground ""))
                                      (cons 1000 "PROJECT-H")(cons 1040(if height_ground height_ground 0.))
                                      ))
                   
                   )
                  ;;--- テンプレートから作った特殊部 / マンホール -------------------
                  ;;  形状の作り方はテンプレート側にしかないので、ここでは持たず
                  ;;  makeparts をもう一度呼んで同じ形を作り直す。
                  ;;  列 : 名前, 色, テンプレート名, 投影図名, 投影高さ,
                  ;;       (特殊部) 延長, 基準点X, 基準点Y, 基準点Z,
                  ;;       (マンホール) 中心X, 中心Y, 天端Z, 総高さ,
                  ;;       向きX, 向きY, テンプレートのパラメータ…
                  ((or(= str "CCBOXTEMP")(= str "MANHOLETEMP"))
                   ((lambda( / bool_mh ls_field ls_head ii ls_rest ls_val
                              int_coltemp str_temp str_prjd num_prjh
                              num_a num_b num_c num_d num_vx num_vy
                              p_base vecx num_len num_total ls_part)
                      (setq bool_mh(= str "MANHOLETEMP")
                            ls_field(cdr lst)
                            ls_head(list)
                            ls_rest ls_field
                            ii -1)
                      ;;先頭 11 列が見出し。12 列目からがテンプレートのパラメータ
                      (while(<(setq ii(1+ ii))11)
                        (setq ls_head(cons(car ls_rest)ls_head)
                              ls_rest(cdr ls_rest)))
                      (setq ls_head(reverse ls_head)
                            ls_val(mapcar 'atof ls_rest)
                            ls_val(if bool_mh(td3d_mh_fill ls_val)
                                    (td3d_tmp_fill ls_val)))

                      (mapcar 'set
                              '(str_name int_coltemp str_temp str_prjd num_prjh
                                         num_a num_b num_c num_d num_vx num_vy)
                              ls_head)
                      (setq int_coltemp(atoi int_coltemp)
                            num_prjh(atof num_prjh)
                            vecx(list(atof num_vx)(atof num_vy)0.)
                            vecx(if(<(distance(list 0. 0. 0.)vecx)1e-8)
                                    (list 1. 0. 0.)
                                  (unit_vector vecx)))

                      (if(=(caar ls_str_in)"ATTRIBUTE")
                          (setq ls_xdata_att(cdar ls_str_in)
                                ls_str_in(cdr ls_str_in)))

                      (if bool_mh
                          (setq p_base(list(atof num_a)(atof num_b)(atof num_c))
                                num_total(atof num_d)
                                ls_part(td3d_mh_makeparts
                                        ls_val p_base vecx
                                        (if(< num_total 1e-8)nil num_total)
                                        (getvar "CLAYER")))
                        (setq num_len(atof num_a)
                              p_base(list(atof num_b)(atof num_c)(atof num_d))
                              ls_part(td3d_tmp_makeparts
                                      ls_val p_base vecx num_len(getvar "CLAYER"))))

                      (mapcar
                       '(lambda(a / vna str_part)
                          (setq vna(car a)str_part(cdr a))
                          ;;鉄蓋だけは配置時と同じく色を固定する
                          (vl-catch-all-apply
                           'vla-put-color
                           (list vna(if(and bool_mh(= str_part "MHCOVER"))
                                        td3d_mh_covercolor int_coltemp)))
                          (set_xda vna
                                   (list(cons 1000(if bool_mh "MANHOLESOLID"
                                                    "CCBOXTEMPSOLID"))
                                        (cons 1000 "PART")(cons 1000 str_part)
                                        (cons 1000 "TEMPLATE")(cons 1000 str_temp))
                                   "terraduct3d")
                          (setq ls_vnam_copy(cons vna ls_vnam_copy)))
                       ls_part)

                      ;;ブロックに付ける XDATA は配置時とまったく同じ並びにする
                      (setq ls_xdata
                            (append
                             (list(cons 1000(if bool_mh "MANHOLEBLOCK"
                                              "CCBOXTEMPBLOCK"))
                                  (cons 1000 "TEMPLATE")(cons 1000 str_temp)
                                  (cons 1000 "PROJECT-D")(cons 1000 str_prjd)
                                  (cons 1000 "PROJECT-H")(cons 1040 num_prjh))
                             (if bool_mh
                                 (list(cons 1000 "CENTER-X")(cons 1040(car p_base))
                                      (cons 1000 "CENTER-Y")(cons 1040(cadr p_base))
                                      (cons 1000 "TOPZ")(cons 1040(caddr p_base))
                                      (cons 1000 "VEC-X")(cons 1040(car vecx))
                                      (cons 1000 "VEC-Y")(cons 1040(cadr vecx))
                                      (cons 1000 "TOTALH")(cons 1040 num_total))
                               (list(cons 1000 "LENGTH")(cons 1040 num_len)
                                    (cons 1000 "BASE-X")(cons 1040(car p_base))
                                    (cons 1000 "BASE-Y")(cons 1040(cadr p_base))
                                    (cons 1000 "BASE-Z")(cons 1040(caddr p_base))
                                    (cons 1000 "VEC-X")(cons 1040(car vecx))
                                    (cons 1000 "VEC-Y")(cons 1040(cadr vecx))))
                             (apply 'append
                                    (mapcar '(lambda(a val)
                                               (list(cons 1000(car a))(cons 1040 val)))
                                            (if bool_mh(td3d_mh_paramdef)
                                              (td3d_tmp_paramdef))
                                            ls_val))))
                      ))
                   )

                  ((= str "PROJECTROAD")
                   (setq lst(cddr lst)
                         int_col(atoi(car lst))hand_road(cadr lst)ls_p(list))
                   
                   (if(=(caar ls_str_in)"ATTRIBUTE")
                       (setq ls_xdata_att(cdar ls_str_in)
                             ls_str_in(cdr ls_str_in)))
                   
                   (while(progn(setq lst(car ls_str_in)ls_str_in(cdr ls_str_in)
                                     str_type(car lst))
                               (= str_type "POINT"));;PROJECTROADEND
                     
                     (setq i(atoi(cadr lst))
                           lst(mapcar 'atof(cddr lst))
                           p(take_list lst 3)
                           )
                     (mapcar '(lambda(a)(setq ls_p(cons a ls_p)))p)
                     (if(= i 1)
                         (setq v(vla-addcircle
                                 (vla-get-modelspace(vla-get-activedocument(vlax-get-acad-object)))
                                 (vlax-3d-point p)radius_node)
                               ls_vnam_copy(cons v ls_vnam_copy)
                               ;;ソリッドがvlaaddできないのでコピーが残っている
                               )
                       )

                     (if(setq lst(cdddr lst))
                         (progn
                           (setq ang(car lst)
                                 v(vla-addtext
                                   (vla-get-modelspace(vla-get-activedocument(vlax-get-acad-object)))
                                   "arc"(vlax-3d-point(cdr lst))radius_node)
                                 ls_vnam_copy(cons v ls_vnam_copy))
                           (vla-put-Alignment v 13)
                           (vla-put-rotation v ang)
                           (vla-put-TextAlignmentPoint v(vlax-3d-point(cdr lst)))
                           ))
                     
                     )

                   (setq ls_p(reverse ls_p))
                   (setq array_p(vlax-make-safearray vlax-vbDouble(cons 0 (1-(length ls_p)))))
                   (vlax-safearray-fill array_p ls_p)
                   (setq vnam(vla-Add3dPoly
                              (vla-get-ModelSpace(vla-get-ActiveDocument(vlax-get-acad-object)))array_p)
                         ls_vnam_copy(cons vnam ls_vnam_copy)
                         )
                   (vla-put-color vnam int_col)

                   (setq ls_xdata(list(cons 1000 "PROJECT")(cons 1000 "PROJECT")(cons 1000 "")))
                   
                   )
                  )
                 
                 (setq ls_vla-release(cons block ls_vla-release))

                 ;;何も作れなかったときは safearray が作れずエラーになるので飛ばす
                 (if(null ls_vnam_copy)T
                   (vla-copyobjects
                    (vla-get-ActiveDocument(vlax-get-acad-object))
                    (vlax-make-variant
                     (vlax-safearray-fill
                      (vlax-make-safearray
                       vlax-vbObject(cons 0(1-(length ls_vnam_copy))) )
                      ls_vnam_copy)
                     )
                    block))

                 (vlax-for
                  obj block
                  
                  (cond
                   ((=(vla-get-ObjectName obj)"AcDb3dPolyline")
                    (setq ls_hand_road(cons(cons hand_road(vla-get-handle obj) )ls_hand_road))
                    )
                   )
                  )
                 
                 (setq vnam(vla-InsertBlock
                            (vla-get-ModelSpace(vla-get-ActiveDocument(vlax-get-acad-object)))
                            (vlax-3d-point 0 0 0)str_name 1 1 1 0)
                       )
                 
                 (set_xda vnam ls_xdata "terraduct3d")
                 (if ls_xdata_att
                     (set_xda vnam(mapcar '(lambda(a)(cons 1000 a))ls_xdata_att)
                              "attributedata"))
                 (mapcar '(lambda(v)
                            (vla-delete v)
                            (exckillobj v)
                            )
                         ls_vnam_copy)
                 ))
           
           )

         (x-alert
          (if ls_existblock
              (if(= int_overwrite_readcsv 0)
                  (list ;;既存のブロック名称であったため上書きせずに読込完了しました
                   26082 23384 12398 12502 12525 12483 12463 21517 31216 12391 12354 12387 12383 12383 12417 19978 26360 12365 12379 12378 12395 35501 36796 23436 20102 12375 12414 12375 12383
                   "\n" (vl-princ-to-string ls_existblock)
                   )
                (list ;;既存のブロックを削除して新たに読み込みました
                 26082 23384 12398 12502 12525 12483 12463 12434 21066 38500 12375 12390 26032 12383 12395 35501 12415 36796 12415 12414 12375 12383
                 "\n"(vl-princ-to-string ls_existblock)
                 )
                )
            (list ;;既存のブロック名称と干渉せずすべて読込完了しました
             26082 23384 12398 12502 12525 12483 12463 21517 31216 12392 24178 28169 12379 12378 12377 12409 12390 35501 36796 23436 20102 12375 12414 12375 12383
             )))
         
         (setq ls_existblock(list))
         
         )
        )
       (setq int_selectmenu nil)
       

       
       ))
    
    ;;CLICK,KEYBOAD
    
    )

   (list
    "visible_annotation" ;;edsym
    (cons
     "INITIAL"
     (lambda(bool);;initial
       (if(car bool)
           (progn
             (if(= int_invisible_annotation 1)
                 (setq int_invisible_annotation 0)
               (setq int_invisible_annotation 1))

             
             ((lambda( / array_type array_data )
                (setq xrec(vl-catch-all-apply 'vla-Item (list asis_session "PARAMETER")))
                (vla-GetXRecordData xrec 'array_type 'array_data )
                (setq lst(if array_data
                             (mapcar 'vlax-variant-value
                                     (vlax-safearray->list array_data)))
                      lst(split_list 2 lst)
                      )

                (setq str(vl-symbol-name 'int_invisible_annotation)
                      lst(subst(list str int_invisible_annotation)(assoc str lst)lst)
                      lst(apply 'append lst)
                      lst(mapcar
                          '(lambda(val / sym str int_type str_type)
                             (setq str_type(type val))
                             (cons(if(= str_type 'REAL)1040
                                    (if(= str_type 'INT)1071
                                      (if(= str_type 'STR)1000
                                        )))
                                  val)
                             )
                          lst)
                      array_data(vlax-make-safearray
                                 vlax-vbVariant(cons 0(1-(length lst))))
                      array_type(vlax-make-safearray
                                 vlax-vbInteger(cons 0(1-(length lst))))
                      )
                (vlax-safearray-fill array_type(mapcar 'car lst))
                (vlax-safearray-fill array_data(mapcar 'cdr lst))
                (vla-SetXRecordData xrec array_type array_data )
                ))

             ((lambda( / num ls_out vnam vnam_insert)
                (setq set_ent(ssget "X"(list(cons 0 "INSERT")(list -3(list "terraduct3d"))))
                      num(if set_ent(sslength set_ent)0) )
                (while(>(setq num(1- num))-1)
                  (setq vnam_insert(vlax-ename->vla-object(ssname set_ent num)))
                  (vla-getXData vnam_insert "terraduct3d" 'array_Type 'array_Data )
                  (setq ls_xdata
                        (if array_data
                            (split_list 0(mapcar 'vlax-variant-value
                                                 (vlax-safearray->list array_data))))
                        str_xdata(cdr(assoc "terraduct3d" ls_xdata))
                        )
                  
                  (setq str_insertname(vla-get-name vnam_insert)
                        vnam(vla-Item(vla-get-Blocks (vla-get-ActiveDocument(vlax-get-acad-object)))
                                     str_insertname)
                        )
                  (vlax-for
                   obj vnam
                   (setq str(vla-get-objectname obj))
                   (if(or(= str "AcDbRotatedDimension")(= str "AcDb3PointAngularDimension"))
                       (vla-put-visible obj(if(= int_invisible_annotation 1) :vlax-false :vlax-true)))
                   )

                  
                  ;; (vla-delete vnam_insert)
                  ;; (setq vnam_insert
                  ;;       (vla-InsertBlock
                  ;;        (vla-get-ModelSpace(vla-get-ActiveDocument(vlax-get-acad-object)))
                  ;;        (vlax-3d-point 0 0 0)str_insertname 1 1 1 0)
                  ;;       )
                  ;; (set_xda vnam_insert(list(cons 1000 str_xdata))"terraduct3d")

                  )

                (vla-Regen(vla-get-ActiveDocument(vlax-get-acad-object))acAllViewports)

                
                ))
             
             
             (setq
              func_guidemenu
              (lambda()nil )
              
              ls_guideexplane
              (mapcar
               'mix_strasc
               (list ))
              
              ls_guidemenu
              (list
               )
              
              
              )
             
             (setq bool_replacegrread T int_grread 2 elem_grread 13)
             ) )
       
       (if(cadr bool) (list ) )
       ))
    
    (cons
     "KEYBOAD"
     (lambda();;gr2
       (if(or(= elem_grread 13)(= int_grread 25))
           (setq str_edit "home"))
       ))

    ;;CLICK,KEYBOAD
    
    )
   
   
   
   (list
    "refreshground" ;;edsym
    (cons
     "INITIAL"
     (lambda(bool);;initial
       (if(car bool)
           (progn
             ;;temp
             (setq bool_point nil
                   bool_selectent nil bool_select nil int_selectmode -1
                   ls_vnam_select nil
                   ls_ssget(list(cons 0 "INSERT"))
                   xtype_ssget "DUCTBLOCK,CCBOXBLOCK,CCBOXTEMPBLOCK,MANHOLEBLOCK"
                   xdata_ssget "terraduct3d"
                   )


             (setq
              func_guidemenu
              (lambda()
                ;;投影した管路、特殊部を対象に選択でき、その他のものは選択しようとしてもハイライトされません
                ;;\n何も選択しないとき、すべて選択したことになります
                ;;\n選択有り無し
                (mix_strasc
                 (list 25237 24433 12375 12383 31649 36335 12289 29305 27530 37096 12434 23550 35937 12395 36984 25246 12391 12365 12289 12381 12398 20182 12398 12418 12398 12399 36984 25246 12375 12424 12358 12392 12375 12390 12418 12495 12452 12521 12452 12488 12373 12428 12414 12379 12435
                       "\n" 20309 12418 36984 25246 12375 12394 12356 12392 12365 12289 12377 12409 12390 36984 25246 12375 12383 12371 12392 12395 12394 12426 12414 12377
                       "\n" 36984 25246 12304
                       (if ls_vnam_select(list 26377 12426)(list 28961 12375)) 12305
                       )
                 ) )
              
              ls_guideexplane
              (mapcar
               'mix_strasc
               (list(list " - " 25237 24433 12375 12383 31649 36335 12289 29305 27530 37096 12434 23550 35937 12395 36984 25246 12391 12365 12289 12381 12398 20182 12398 12418 12398 12399 36984 25246 12375 12424 12358 12392 12375 12390 12418 12495 12452 12521 12452 12488 12373 12428 12414 12379 12435)
                    (list " - " 20309 12418 36984 25246 12375 12390 12356 12394 12356 12392 12365 22259 38754 20869 12398 12377 12409 12390 12364 23550 35937 12395 12394 12426 12414 12377 )
                    ))
              ;;何も選択していないとき図面内のすべてが対象になります
              
              ls_guidemenu
              (list

               (list(list 76);; 地表面標高
                    (cons "ITEM"(list 22320 34920 38754 27161 39640))
                    (cons "STATUS"
                          (lambda()
                            (if str_lasground
                                (mix_strasc
                                 (list "{\\C" str_gcol_c ";" 12487 12540 12479 "} : "
                                       (vl-string-subst "" "lasgrid-" str_lasground)))
                              (if height_ground
                                  (mix_strasc
                                   (list"{\\C" str_gcol_g ";" 27161 39640 "} : "
                                        (as-numstr height_ground)))
                                (mix_strasc
                                 (list "{\\C" str_gcol_r ";"
                                       36984 25246 12373 12428 12390 12356 12414 12379 12435 "}"))
                                ))
                            ))
                    (cons "LOADFUNCTION"(lambda()(settile_selectground)))
                    (cons "HELP"(lambda()(mix_strasc(list 20351 29992 12377 12427 27161 39640 12434 "\n- las" 35501 36796 "\n- xml" 35501 36796 "\n- " 19968 23450 27161 39640 12398 25968 20516 20837 21147 "\n" 12363 12425 36984 25246 12391 12365 12414 12377 ))))
                    )
               
               (list(list 49);;実行
                    (cons "ITEM"(list 23455 34892 ))
                    (cons "NEXTMODE" str_edit);;

                    (cons "LOADFUNCTION"
                          (lambda()(setq str_next nil ) ))
                    (cons "CLICKFUNCTION"
                          (lambda()(setq bool_replacegrread T int_grread 2 elem_grread 49) ))
                    
                    )
               
               (list(list 80 );;P選択モード切替
                    (cons "ITEM"(list 36984 25246 12514 12540 12489 20999 26367 ))
                    (cons "INPUTSWITCH"
                          (lambda()
                            (if(= int_selectmode -1)
                                (list nil(mix_strasc
                                          (list "{\\C" str_gcol_p ";"
                                                21336 20307 36984 25246 12398 12415 "}")))
                              (list 'int_selectmode
                                    (mapcar 'mix_strasc
                                            (list(list "{\\C" str_gcol_y ";" 36984 25246 "}")
                                                 (list "{\\C" str_gcol_c ";" 35299 38500 "}")))
                                    ))
                            ) )
                    (cons "HELP"(lambda()str_guide_selectmode))
                    )
               
               ;; (list(list nil)
               ;;      (cons "ITEM"(list ))
               ;;      (cons "BOOL"
               ;;            (lambda()
               ;;              nil
               ;;              ))
               ;;      (cons "STATUS" (lambda( / bool_depth ii ls_out) "" ))
               ;;      )
               
               (list(list "ENTER");;メインメニューへ
                    (cons "ITEM"(list 12513 12452 12531 12513 12491 12517 12540 12408))
                    (cons "NEXTMODE" "home")
                    )
               
               )
              
              
              )
             
             ))
       
       (if(cadr bool) (list ) )
       ))
    
    
    (cons
     "KEYBOAD"
     (lambda( / ls_str_out num ls_out_parameter str_out bool_loop
                p_new ls_pnew int_outofground ls_skipblock )

       ;;地表面データの範囲外だった点の数と、更新できなかったブロック名
       ;;str_warned_lasground は project_to_ground の警告を1回だけにするための記録
       (setq int_outofground 0 ls_skipblock(list) str_warned_lasground nil)

       (if(vl-position str_editreturn(list "insertarc" "tempdistlength"))T
         (progn
           (setq ls_vnam_refreshproject(list))
           (if ls_vnam_select T
             ((lambda( / num ls_out vnam)
                (setq set_ent(ssget "X"(list(cons 0 "INSERT")(list -3(list "terraduct3d"))))
                      num(if set_ent(sslength set_ent)0) )
                (while(>(setq num(1- num))-1)
                  (setq vnam(vlax-ename->vla-object(ssname set_ent num))
                        ls_vnam_select(cons vnam ls_vnam_select))
                  )
                ))
             ))
         )

       (setq bool_loop T)

       (while ls_vnam_select
         (setq vnam(car ls_vnam_select))
         (setq ls_vnam_select(cdr ls_vnam_select));;bool_loopを使わなければいけない仕組みを考えていたはず
         
         (vla-getXData vnam "terraduct3d" 'array_Type 'array_Data )
         (if array_data
             (setq ls_xdata
                   (split_list 0(mapcar 'vlax-variant-value
                                        (vlax-safearray->list array_data)))
                   str_type(cdr(assoc "terraduct3d" ls_xdata)))
           (setq str_type nil) )

         (cond
          ((= str_type "PROJECT"))
          ((= str_type "DUCTBLOCK")

           (setq str_insertname(vla-get-name vnam)
                 vnam_insert(vla-Item(vla-get-Blocks (vla-get-ActiveDocument(vlax-get-acad-object)))
                              str_insertname)
                 )

           (setq ls_vnam_duct(list)num_duct 0 )
           (vlax-for
            obj vnam_insert
            (vla-getXData obj "terraduct3d" 'array_Type 'array_Data )

            (if array_data
                (setq ls_xdata
                      (split_list 0(mapcar 'vlax-variant-value
                                           (vlax-safearray->list array_data)))
                      str_type(cdr(assoc "terraduct3d" ls_xdata)))
              (setq str_type nil) )

            (setq ls_vnam_duct
                  (cons
                   (cond
                    ((= str_type "LINE")
                     (setq ii(cdr(assoc "NUM" ls_xdata)) num_duct(max num_duct ii))
                     (list(list str_type ii) (list "OBJ" obj))
                     )
                    ((= str_type "DEPTH")
                     (if(setq str_road(cdr(assoc "ROAD" ls_xdata)))
                         ((lambda( / block v str)
                            (if(vl-catch-all-error-p
                                (setq block(vl-catch-all-apply 'vla-Item(list vnam_blocktable str_road))))
                                (if(setq entna_road(handent str_road))
                                    (setq v(vlax-ename->vla-object entna_road)
                                          block(vla-Item(vla-get-Blocks
                                                         (vla-get-ActiveDocument(vlax-get-acad-object)))
                                                        (vla-get-name v))
                                          ))
                              )
                            
                            (if(vl-catch-all-error-p block)T
                              (if(vl-position block ls_vnam_refreshproject)T
                                (setq ls_vnam_refreshproject(cons block ls_vnam_refreshproject))))
                            )) )
                     
                     (setq entna(vlax-vla-object->ename obj)
                           ls_gcode(entget entna)
                           p13(cdr(assoc 13 ls_gcode))
                           p14(cdr(assoc 14 ls_gcode))
                           delta_z(-(caddr p14)(caddr p13))
                           p_new(car(project_to_ground
                                     (list p13)(list 0. 0. 1.)
                                     (list str_lasground height_ground)))
                           )
                     ;;地表面データの範囲外だと nil が返る。
                     ;;そのまま (caddr nil) を計算すると型エラーで更新が途中で止まるので、
                     ;;その点は動かさずに数だけ数えて先へ進む
                     ;;else 側は2つの式があるので progn でまとめる
                     ;;(if は test then else の3引数まで)
                     (if(null p_new)
                         (setq int_outofground(1+ int_outofground)
                               p14(carxyz p13(+(caddr p13)delta_z)))
                       (progn
                         (setq p13 p_new
                               zz(+(caddr p13)delta_z) p14(carxyz p13 zz)
                               str(depth_level_str p13 p14)
                               ls_gcode(subst(cons 13 p13)(assoc 13 ls_gcode)ls_gcode)
                               ls_gcode(subst(cons 14 p14)(assoc 14 ls_gcode)ls_gcode)
                               ls_gcode(subst(cons 1 str)(assoc 1 ls_gcode)ls_gcode)
                               )
                         (entmod ls_gcode)))
                     (setq ii(cdr(assoc "NUM" ls_xdata))jj(cdr(assoc "SIDE" ls_xdata)))


                     (list(list "DEPTH" ii jj ) (list "POINT" p13 p14) )
                     )
                    
                    ((= str_type "ARC")
                     (list(list str_type
                                (cdr(assoc "NUM" ls_xdata))
                                (cdr(assoc "SIDE" ls_xdata))
                                )
                          (list "OBJ" obj(vlax-vla-object->ename obj))
                          (list "RADIUS"(cdr(assoc "RADIUS" ls_xdata)))
                          )
                     )
                    
                    ((= str_type "CENTERLINE")
                     (list(list str_type 0)(list "OBJ" obj) (list "COLOR"(vla-get-color obj)) )
                     )
                    ((= str_type "DUCTSOLID")
                     (setq diam_duct_temp(cdr(assoc "DIAM" ls_xdata)))
                     (list(list str_type 0)(list "OBJ" obj)(list "COLOR"(vla-get-color obj))
                          (list "DIAM" diam_duct_temp)
                          )
                     )
                    ((= str_type "CONMESH")
                     (append
                      (list(list str_type 0)(list "OBJ" obj)(list "COLOR"(vla-get-color obj)))
                      (mapcar '(lambda(str)(list str(cdr(assoc str ls_xdata))))
                              (list "CORNER" "WIDTH" "HEIGHT" "FILET")))
                     )
                    )
                   ls_vnam_duct))

            ;; (setq str(vla-get-objectname obj))
            ;; (if(or(= str "AcDbRotatedDimension")(= str "AcDb3PointAngularDimension"))
            ;;     (vla-put-visible obj(if(= int_invisible_annotation 1) :vlax-false :vlax-true)))
            )
           (setq pitch_mesh(min pitch_project diam_duct_temp))
           (if(<(abs pitch_mesh)1e-8)
               (setq pitch_mesh diam_duct_temp))
           
           
           
           (setq int_max_duct num_duct num_duct(1+ num_duct)ls_pline1(list)
                 ls_arcpoint(list))
           (while(>(setq num_duct(1- num_duct))-1)
             (setq lst(assoc(list "DEPTH" num_duct 0) ls_vnam_duct)
                   p_line00(caddr(assoc "POINT" lst))
                   lst(assoc(list "DEPTH" num_duct 1) ls_vnam_duct)
                   p_line01(caddr(assoc "POINT" lst))
                   lst(assoc(list "LINE" num_duct) ls_vnam_duct)
                   vnam_line(cadr(assoc "OBJ" lst))
                   vec_line0(unit_vector(mapcar '- p_line00 p_line01))
                   )
             (vla-put-startpoint vnam_line(vlax-3d-point p_line00))
             (vla-put-endpoint vnam_line(vlax-3d-point p_line01))

             (if(and(setq lst0(assoc(list "ARC" num_duct 0) ls_vnam_duct))
                    (setq lst1(assoc(list "ARC" num_duct 1) ls_vnam_duct))
                    )
                 
                 ((lambda(  / lst bool ls_p px vec pc pco pho p int_temp p_arcstart)
                    ;;p起点

                    (setq entna_arc0(caddr(assoc "OBJ" lst0))
                          entna_arc1(caddr(assoc "OBJ" lst1))
                          p_arcstart(cdr(assoc 13(entget entna_arc0)))
                          )
                    (vla-put-startpoint vnam_cross_temp(vlax-3d-point p_arcstart))
                    (vla-put-endpoint vnam_cross_temp(vlax-3d-point(mapcar '+ p_arcstart(list 0 0 1.))))
                    (setq p_arcstart(car(get_inters_point_vna vnam_line vnam_cross_temp 11)))
                    
                    (setq int_temp 0)

                    ((lambda( /  delta_arc bool_loop);;initial
                       (setq length_s 0. radius_arcmove(cadr(assoc "RADIUS" lst0))
                             vec_normal(unit_vector(cross_product vec_line1 vec_line0)))
                       (if(<(distance(list 0 0 0)vec_normal)1e-8)
                           (setq vec_normal(unit_vector(cross_product(mapcar '- p_line10 p_line00)vec_line0))
                                 bool_linetype 0
                                 )
                         (setq bool_linetype 1))
                       
                       (setq dist_normal(apply '+(mapcar '* vec_normal p_line00)))
                       
                       (if(= bool_linetype 1)
                           (if(<(abs(- dist_normal(apply '+(mapcar '* vec_normal p_line10))))1e-8)T
                             (setq bool_linetype 2)))
                       
                       (setq point_decide nil ls_limit0 nil ls_limit1 nil)
                       (cond
                        ((= bool_linetype 0)
                         
                         (setq vec_linenormal(cross_product vec_normal vec_line0)
                               dist_linenormal(abs(apply '+(mapcar '* vec_linenormal(mapcar '- p_line00 p_line10))))
                               )
                         ;; (if(= int_editarcposition_temp 3)
                         ;;     (setq radius_arcmove(max radius_bend_temp(* 0.5 dist_linenormal))
                         ;;           int_editarcposition_temp 1 ))
                         (setq dist_lineparallel
                               (sqrt(* dist_linenormal(-(* 2. radius_arcmove)dist_linenormal)))
                               )
                         
                         )
                        ((= bool_linetype 1)
                         
                         (setq vec_nline0(cross_product vec_line0 vec_normal);;逆；重要
                               vec_nline1(cross_product vec_normal vec_line1))

                         (vla-put-startpoint vnam_cross_temp(vlax-3d-point p_line10))
                         (vla-put-endpoint vnam_cross_temp(vlax-3d-point p_line11))
                         (setq p_crossx(car(get_inters_point_vna vnam_line vnam_cross_temp 11)))
                         
                         ;; (mapcar
                         ;;  'set '(vec_nline0 vec_nline1 p_centerx p_arcstartx p_arcendx p_arcwayx p_crossx)
                         ;;  lst)


                         ;; (if(= int_editarcposition_temp 3)
                         ;;     ((lambda( / vec_normal vec_nline0 vec_nline1)
                         ;;        (setq bool_distline T radius_limit radius_bend_temp num_limit 100
                         ;;              vec_normal(unit_vector(cross_product vec_line0 vec_line1))
                         ;;              vec_nline0(cross_product vec_line0 vec_normal)
                         ;;              vec_nline1(cross_product vec_normal vec_line1)
                         ;;              )
                         
                         ;;        (while(= int_editarcposition_temp 3)
                         ;;          (setq p_h00(mapcar '(lambda(a b)(+ a(* radius_arcmove b)))
                         ;;                             p_line01 vec_nline0)
                         ;;                p_h01(mapcar '(lambda(a b)(+ a(* -1 radius_arcmove b)))
                         ;;                             p_line01 vec_nline0)
                         ;;                p_h10(mapcar '(lambda(a b)(+ a(* radius_arcmove b)))
                         ;;                             p_line10 vec_nline1)
                         ;;                p_h11(mapcar '(lambda(a b)(+ a(* -1 radius_arcmove b)))
                         ;;                             p_line10 vec_nline1)
                         ;;                dist_line_tan
                         ;;                (-(min(distance p_h00 p_h11)(distance p_h01 p_h10))
                         ;;                  (* 2 radius_arcmove))
                         ;;                )
                         
                         ;;          ;;todo円弧の作り方を変えるか
                         ;;          (setq num_limit(1- num_limit))
                         ;;          (cond
                         ;;           ((< num_limit 0)
                         ;;            (setq int_editarcposition_temp 1)
                         ;;            )
                         ;;           ((<(abs dist_line_tan)1e-8)
                         ;;            (setq int_editarcposition_temp 1))
                         ;;           ((> dist_line_tan 0.)
                         ;;            (if(< delta_arcmove 0)(setq delta_arcmove(* -0.1 delta_arcmove)))
                         ;;            (setq radius_arcmove(+ radius_arcmove delta_arcmove))
                         ;;            )
                         
                         ;;           ((<(- radius_arcmove radius_limit)1e-8)
                         ;;            (setq radius_arcmove radius_limit int_editarcposition_temp 1))
                         ;;           (T
                         ;;            (if(> delta_arcmove 0)(setq delta_arcmove(* -0.1 delta_arcmove)))
                         ;;            (setq radius_arcmove(+ radius_arcmove delta_arcmove)))
                         ;;           )
                         ;;          )
                         ;;        (setq radius_arcmove
                         ;;              (atof(rtos radius_arcmove 2 int_unitarcautoma)))
                         ;;        ) ))
                         
                         ;;限界計算は insertarc と共通の arc2_limits に統合した
                         (arc2_limits 1e-8 1000)
                         )
                        ((= bool_linetype 2)
                         (setq vec_normal(unit_vector(cross_product(mapcar '- p_line10 p_line01)vec_line0))
                               dist_normal(apply '+(mapcar '* vec_normal p_line01)))

                         ;;(setq bool_distline T radius_limit radius_bend_temp)
                         (setq num_limit 100 )
                         
                         ;; (if(= int_editarcposition_temp 3)
                         ;;     (progn
                         ;;       (setq length_arc_min 0
                         ;;             vec_ends(mapcar '- p_line10 p_line01)
                         ;;             length_arc_max(distance p_line01 p_line10)
                         ;;             variable_a(expt length_arc_max 2)
                         ;;             variable_b(* 2.(apply '+(mapcar '* vec_ends vec_line0)))
                         ;;             variable_c(* 2.(apply '+(mapcar '* vec_ends vec_line1)))
                         ;;             variable_d(* 2.(1+(apply '+(mapcar '* vec_line0 vec_line1))))
                         ;;             )
                               
                         ;;       (while(= int_editarcposition_temp 3)
                                 
                         ;;         (setq length_arc_x
                         ;;               (/(+ variable_a(* length_arc_min variable_b))
                         ;;                 (+ variable_c(* length_arc_min variable_d)))
                         ;;               vec_common
                         ;;               (mapcar '(lambda(a b c)
                         ;;                          (+ a(* length_arc_min b)(* -1. length_arc_x c)))
                         ;;                       vec_ends vec_line0 vec_line1)
                         ;;               vec_common(unit_vector vec_common)
                         ;;               radius1(apply '+(mapcar '* vec_line0 vec_common))
                         ;;               radius1(* length_arc_min(sqrt(/(- 1 radius1)(+ 1 radius1))))
                         ;;               radius2(apply '+(mapcar '* vec_line1 vec_common))
                         ;;               radius2(* length_arc_x(sqrt(/(+ 1 radius2)(- 1 radius2))))
                         ;;               dist_line_tan(- radius1 radius2)
                         ;;               )

                         ;;         (setq num_limit(1- num_limit))
                         ;;         (cond
                         ;;          ((< num_limit 0)(setq int_editarcposition_temp 1))
                         ;;          ((<(abs dist_line_tan)1e-8)
                         ;;           (setq radius_arcmove(max radius_arcmove radius1))
                         ;;           (setq int_editarcposition_temp 1))
                         ;;          ((< dist_line_tan 0.)
                         ;;           (if(< delta_arcmove 0)(setq delta_arcmove(* -0.1 delta_arcmove)))
                         ;;           (setq length_arc_min(+ length_arc_min delta_arcmove))
                         ;;           )
                         ;;          (T
                         ;;           (if(> delta_arcmove 0)(setq delta_arcmove(* -0.1 delta_arcmove)))
                         ;;           (setq length_arc_min(+ length_arc_min delta_arcmove)))
                         ;;          )
                         ;;         )

                         ;;       (setq radius_arcmove
                         ;;             (atof(rtos radius_arcmove 2 int_unitarcautoma)))
                               
                         ;;       ))



                         ;;限界計算(2方向の探索)は insertarc と共通の arc2_limits に統合した
                         (arc2_limits 1e-8 1000)

                         )
                        )
                       
                       
                       ))
                    
                    
                    ;;円弧2本の計算は insertarc と共通の func_insertarc_move に統合した。
                    ;;ここは常に起点側基準(int_temp=0)。
                    ;;ねじれで解が無いとき func_insertarc_move は値を入れないので、
                    ;;前回値が残らないよう先に nil にしておく(旧コードと同じ挙動)
                    (setq ls_arc_parameter nil)
                    (func_insertarc_move p_arcstart 'ls_arc_parameter 0)

                    (mapcar
                     '(lambda( lst e ii / vnam vec_normal pc p0 p1 p2 length_straight e_out)
                        (mapcar 'set '(pc p0 p1 p2 vec_normal length_straight)lst)
                        (setq ls_arcpoint(cons(list(list num_duct ii)pc p0 p1 p2 vec_normal)ls_arcpoint))

                        (setq dist_normal(apply '+(mapcar '* pc vec_normal)))
                        (make_arcdimension
                         e(list pc p0 p1 p2 rr vec_normal dist_normal
                                (arc2_dimtext rr p1 p2)
                                str_dimstyle_ductlevel))
                        
                        ;; (if e
                        ;;     (setq ls_vnam_duct
                        ;;           (subst(list(assoc "ARC" ls_current)
                        ;;                      (assoc "OBJ" ls_current)
                        ;;                      (cons "RADIUS" rr)
                        ;;                      (assoc "POSITION" ls_current)
                        ;;                      )
                        ;;                 ls_current ls_vnam_duct)
                        ;;           vnam(caddr(assoc "OBJ" ls_current))
                        ;;           )
                        ;;   (progn
                        ;;     (setq vnam(vlax-ename->vla-object e_out)
                        ;;           ls_vnam_duct
                        ;;           (subst(list(assoc "ARC" ls_current)
                        ;;                      (list "OBJ" e_out vnam)
                        ;;                      (cons "RADIUS" rr)
                                             
                        ;;                      (assoc "POSITION" ls_current)
                        ;;                      )
                        ;;                 ls_current ls_vnam_duct)
                        ;;           )
                        ;;     (setq ls_p_dimtext (cons(cons vnam p2) ls_p_dimtext))
                        ;;     (vla-put-Arrowhead1Type vnam 19)
                        ;;     (vla-put-Arrowhead2Type vnam 19)
                        ;;     (vla-put-ExtLine1Suppress vnam -1)
                        ;;     (vla-put-ExtLine2Suppress vnam -1)
                        ;;     (vla-put-HorizontalTextPosition vnam 3)
                        ;;     (vla-put-TextInsideAlign vnam 0)
                        ;;     (vla-put-VerticalTextPosition vnam 2)
                        ;;     (addkillobj vnam)
                        ;;     ))

                        )
                     ls_arc_parameter
                     (list entna_arc0 entna_arc1) (list 0 1)
                     )
                    
                    )))

             (setq p_line10 p_line00 p_line11 p_line01
                   vec_line1(mapcar '- vec_line0)
                   )
             )
           
           
           
           ;;solid
           (setq num_duct -1 ls_pmesh(list)ls_pbar(list))
           (setq p0(caddr(assoc "POINT"(assoc(list "DEPTH" 0 0)ls_vnam_duct))) )
           
           (while(<=(setq num_duct(1+ num_duct))int_max_duct)
             (if(setq ls_arc0(cdr(assoc(list num_duct 0)ls_arcpoint))) ;;pc p0 p1 p2 vec_normal)
                 (setq p1(cadr ls_arc0)ls_arc1(cdr(assoc(list num_duct 1)ls_arcpoint)))
               (setq p1(caddr(assoc "POINT"(assoc(list "DEPTH" num_duct 1)ls_vnam_duct))))
               )
             
             (setq vec0(unit_vector(mapcar '- p1 p0)))
             
             (if ls_pmesh T
               (setq ls_pmesh(list(list p0 vec0))
                     ls_pbar(list(list p0 nil vec0))))

  
             
             ;; (setq ls_pbar(cons(list p1 nil vec0) ls_pbar))
             
             
            ;; (vnam_line1;;最終回限定
            ;;  (setq ls_pbar(cons(list p10 nil(unit_vector(mapcar '- p11 p10)))
            ;;                    ls_pbar))
            ;;  )

             (if ls_arc0
                 (mapcar
                  '(lambda(lst i)
                     (if(progn
                          (setq p(caar ls_pbar) p15(car lst) p13(cadr lst) p14(caddr lst)
                                vec_normal(nth 4 lst))
                          (>(distance p13 p14)1e-8)
                          )
                         
                         (progn
                           (setq vec13(mapcar '- p13 p15)rr(distance p15 p13)
                                 vec14(mapcar '- p14 p15)
                                 vec13(mapcar '(lambda(a)(/ a rr))vec13)
                                 vec14(mapcar '(lambda(a)(/ a rr))vec14)
                                 vec0(cross_product vec_normal vec13)
                                 vec1(cross_product vec_normal vec14)
                                 )
                           (if(<(apply '+(mapcar '* vec0 vec14))0)(setq vec0(mapcar '- vec0)))
                           (if(>(apply '+(mapcar '* vec1 vec13))0)(setq vec1(mapcar '- vec1)))
                           
                           (if(<(apply '+(mapcar '*(mapcar '- p13 p)vec0))-1e-8)
                               (setq ls_pbar(cons(list p13 nil vec0)(cdr ls_pbar)))
                             ;; (if(= int_protectcon_temp 2)T
                             ((lambda(p / d n i dd pm)
                                (setq d(distance p p13) n(1+(fix(/ d pitch_mesh))) d(/ d n)
                                      dd(- d))
                                (while(>(setq n(1- n))-1)
                                  (setq dd(+ dd d)
                                        pm(mapcar '(lambda(a b)(+ a(* dd b)))p vec0)
                                        ls_pmesh(cons(list pm vec0)ls_pmesh)
                                        )
                                  )
                                )
                              p)
                             ;; )
                             )

                           (if(<(distance(caar ls_pbar)p13)1e-8)(setq ls_pbar(cdr ls_pbar)))
                           (setq ls_pbar(cons(list p13 p15 vec0)ls_pbar)
                                 ls_pbar(cons(list p14 nil vec1)ls_pbar)
                                 p0 p14 )
                           
                           
                           ;; (if(= int_protectcon_temp 2)T
                           ((lambda( / d n i ang r vec_x vec_y pm dd c s v)
                              (setq ang(atan(distance(cross_product vec13 vec14)(list 0 0 0))
                                            (apply '+(mapcar '* vec13 vec14)))
                                    vec_x(mapcar '(lambda(a)(* a rr))vec13)
                                    vec_y(mapcar '(lambda(a)(* a rr))vec0)
                                    d(* rr ang) n(1+(fix(/ d(min(* 0.5 rr) pitch_mesh))))
                                    d(/ ang n)
                                    ang 0)
                              
                              (while(>(setq n(1- n))0)
                                (setq ang(+ ang d)c(cos ang)s(sin ang)
                                      v(mapcar '(lambda(x y)(+ (* -1 s x)(* c y)))vec13 vec0)
                                      pm(mapcar '(lambda(a x y)(+ a(* c x)(* s y)))p15 vec_x vec_y)
                                      ls_pmesh(cons(list pm v)ls_pmesh)
                                      )
                                )
                              ))
                           ;; )
                           
                           
                           
                           ))
                     )
                  (list ls_arc0 ls_arc1)(list 0 1))

               ((lambda( / d n i dd pm)
                  (setq d(distance p0 p1) n(1+(fix(/ d pitch_mesh))) d(/ d n)
                        dd 0.)
                  
                  (if(< d 1e-8)T
                    (while(>=(setq n(1- n))-1)
                      (setq dd(+ dd d)
                            pm(mapcar '(lambda(a b)(+ a(* dd b)))p0 vec0)
                            ls_pmesh(cons(list pm vec0)ls_pmesh)
                            )
                      )
                    )
                  (setq ls_pbar(cons(list p1 nil vec0)ls_pbar))
                  ))
               
               )
             )

           (setq ls_objcenterline(assoc(list "CENTERLINE" 0)ls_vnam_duct))
           (setq ls_pcenterline(mapcar 'car(reverse ls_pmesh)))
           (setq ls_p(apply 'append ls_pcenterline)
                 array_p(vlax-make-safearray vlax-vbDouble(cons 0(1-(length ls_p)))))
           (vlax-safearray-fill array_p ls_p)
           (vla-put-coordinates(cadr(assoc "OBJ" ls_objcenterline))array_p)

           (setq ls_ductsolid(assoc(list "DUCTSOLID" 0)ls_vnam_duct)
                 diam_duct_temp(cadr(assoc "DIAM" ls_ductsolid))
                 int_colduct_temp(cadr(assoc "COLOR" ls_ductsolid))
                 )
           
           ;; (if(setq lst(assoc(list "SOLID" 0)ls_vnam_duct))
           ;;     (progn
           ;;       (setq vnam(cadr(assoc "OBJ" lst))
           ;;             ls_vnam_duct(vl-remove lst ls_vnam_duct))
           ;;       (vla-delete vnam)
           ;;       (exckillobj vnam)
           ;;       ))
           
           (if(and(= int_ductsolidmesh 1)ls_pbar)
               (progn
                 (setq ls_pbar(reverse ls_pbar)
                       entna(bendpipe_lwpsld
                             (* 0.5 diam_duct_temp) ls_pbar (getvar "CLAYER") nil)
                       vnam(vlax-ename->vla-object entna)
                       )
                 (vla-put-color vnam int_colduct_temp)
                 
                 )
             
             (if ls_pmesh
                 (progn
                   
                   (setq numy 32
                         ls_intmesh(inclist 0 numy)
                         ang_d(/(* 2. pi)numy)
                         r(* 0.5 diam_duct_temp)
                         vecxp nil vecyp nil
                         )
                   
                   (setq ls_pduct
                         (mapcar
                          '(lambda(lst / p v vecx vecy)
                             (setq p(car lst)v(cadr lst)
                                   v(unit_vector v )
                                   vecx(trans-x(list 1 0 0)v(list 0 0 1))
                                   vecy(trans-x(list 0 1 0)v(list 0 0 1))
                                   )

                             (if(if vecxp(>(apply '+(mapcar '* vecx vecxp))0)T)T
                               (setq vecx vecxp))
                             (setq vecxp vecx)
                             (if(<(caddr vecy)0)(setq vecy(mapcar '- vecy)))
                             (mapcar '(lambda(i / c s)
                                        (setq c(cos(* ang_d i))s(sin(* ang_d i)))
                                        (mapcar '(lambda(a x y)(+(* r c x)(* r s y)a))
                                                p vecx vecy))
                                     ls_intmesh)
                             )
                          (reverse ls_pmesh)
                          )
                         
                         numx(length ls_pduct)
                         ls_p(apply 'append(apply 'append ls_pduct))
                         )
                   
                   (setq array_mesh(vlax-make-safearray vlax-vbDouble(cons 0(1-(length ls_p)))))
                   (vlax-safearray-fill array_mesh ls_p)
                   (setq vnam
                         (vla-Add3DMesh
                          (vla-get-ModelSpace(vla-get-ActiveDocument (vlax-get-acad-object)))
                          numx numy array_mesh)
                         )

                   
                   (vla-put-color vnam int_colduct_temp)
                   
                   )
               )
             )

           (set_xda vnam(list(cons 1000 "DUCTSOLID")
                             (cons 1000 "DIAM")(cons 1040 diam_duct_temp)
                             )
                    "terraduct3d")
           (vla-delete(cadr(assoc "OBJ" ls_ductsolid)))
           (vla-copyobjects
            (vla-get-ActiveDocument(vlax-get-acad-object))
            (vlax-make-variant
             (vlax-safearray-fill
              (vlax-make-safearray vlax-vbObject(cons 0 0) )
              (list vnam))
             )
            vnam_insert)
           (vla-delete vnam)
           
           (if(setq ls_conmesh(assoc(list "CONMESH" 0)ls_vnam_duct))
               (progn
                 ;; (setq vnam(cadr(assoc "OBJ" lst))
                 ;;       ls_vnam_duct(vl-remove lst ls_vnam_duct))
                 ;; (vla-delete vnam)
                 ;; (exckillobj vnam)

                 (setq int_corner(cadr(assoc "CORNER" ls_conmesh))
                       width_protect_temp(cadr(assoc "WIDTH" ls_conmesh))
                       height_protect_temp(cadr(assoc "HEIGHT" ls_conmesh))
                       filet_protect_temp(cadr(assoc "FILET" ls_conmesh))
                       )
                 
                 (setq numy int_corner
                       
                       w(* 0.5 width_protect_temp)
                       h(* 0.5 height_protect_temp)
                       f filet_protect_temp
                       
                       ls_pmesh
                       (mapcar
                        '(lambda(lst / p v vecx vecy)
                           (setq p(car lst)v(cadr lst)
                                 v(unit_vector(carxyz v 0.))
                                 vecx(trans-x(list 1 0 0)v(list 0 0 1))
                                 vecy(trans-x(list 0 1 0)v(list 0 0 1))
                                 )
                           
                           (vl-remove
                            nil
                            (mapcar '(lambda(lst / bool iw iwf ih ihf)
                                       (mapcar 'set '(bool iw iwf ih ihf)lst)
                                       (if(vl-position numy bool)
                                           (mapcar '(lambda(a x y)(+(*(+(* iw w)(* iwf f))x)
                                                                    (*(+(* ih h)(* ihf f))y) a))
                                                   p vecx vecy))
                                       )
                                    (list(list(list 8 4)-1  1 1 0)
                                         (list(list 8)  -1  0 1 -1)
                                         (list(list -6 -4)-1 0 0 0)
                                         (list(list 8 4 -6 -4)-1 0 -1 1)
                                         (list(list 8 -6)-1  1 -1 0)
                                         (list(list 8 -6) 1 -1 -1 0)
                                         (list(list 8 4 -6 -4) 1 0 -1 1)
                                         (list(list -6 -4) 1 0 0 0)
                                         (list(list 8)   1  0 1 -1)
                                         (list(list 8 4) 1 -1 1 0)
                                         ))
                            )
                           )
                        (reverse ls_pmesh)
                        )
                       
                       numx(length ls_pmesh)
                       numy(abs numy)
                       ls_p(apply 'append(apply 'append ls_pmesh))
                       )
                 
                 (setq array_mesh(vlax-make-safearray vlax-vbDouble(cons 0(1-(length ls_p)))))
                 (vlax-safearray-fill array_mesh ls_p)
                 (vla-put-coordinates(cadr(assoc "OBJ" ls_conmesh))array_mesh)
                 
                 ;; (setq vnam
                 ;;       (vla-Add3DMesh
                 ;;        (vla-get-ModelSpace(vla-get-ActiveDocument (vlax-get-acad-object)))
                 ;;        numx numy array_mesh)
                 ;;       ls_vnam_duct(cons(list(list "MESH" 0)(list "OBJ" vnam)
                 ;;                             (cons "CORNER" int_corner)
                 ;;                             (cons "WIDTH" width_protect_temp)
                 ;;                             (cons "HEIGHT" height_protect_temp)
                 ;;                             (cons "FILET"  filet_protect_temp)
                 ;;                             )
                 ;;                        ls_vnam_duct)
                 ;;       )
                 
                 ))

           
           )

          ((= str_type "CCBOXBLOCK")
           
           (set_xda vnam
                    (list(cons 1000 "CCBOXBLOCK")
                        (cons 1000 "PROJECT-D")(cons 1000(if str_lasground str_lasground ""))
                        (cons 1000 "PROJECT-H")(cons 1040(if height_ground height_ground 0.))
                        )
                   "terraduct3d")
           
           (setq str_insertname(vla-get-name vnam)
                 vnam_insert(vla-Item(vla-get-Blocks (vla-get-ActiveDocument(vlax-get-acad-object)))
                                     str_insertname)
                 )

           
           (setq px0 nil px1 nil py0 nil py1 nil pz0 nil)
           (vlax-for
            obj vnam_insert
            (vla-getXData obj "terraduct3d" 'array_Type 'array_Data )
            (if array_data
                (setq ls_xdata
                      (split_list 0(mapcar 'vlax-variant-value
                                           (vlax-safearray->list array_data)))
                      str_type(cdr(assoc "terraduct3d" ls_xdata)))
              (setq str_type nil) )
            
            (cond
             ((= str_type "CCBOXWIDTH-X")
              (setq entna(vlax-vla-object->ename obj)
                    ls_gcode(entget entna)
                    px0(cdr(assoc 13 ls_gcode))
                    px1(cdr(assoc 14 ls_gcode))
                    )
              )
             ((= str_type "CCBOXWIDTH-Y")
              (setq entna(vlax-vla-object->ename obj)
                    ls_gcode(entget entna)
                    py0(cdr(assoc 13 ls_gcode))
                    py1(cdr(assoc 14 ls_gcode))
                    )
              )
             ((= str_type "CCBOXVBACANT")
              (setq entna(vlax-vla-object->ename obj)
                    ls_gcode(entget entna)
                    pz0(cdr(assoc 14 ls_gcode))
                    )
              )
             )
            )

           (if(and px0 px1 py0 py1 pz0)
               ((lambda( / p1 p2 p3 p4 vec vecx distx lst zz)
                  
                  (setq vecx(unit_vector(mapcar '- px1 px0))
                        distx(apply '+(mapcar '*(mapcar '- px0 py0)vecx))
                        vec(mapcar '(lambda(a)(* a distx))vecx)
                        p1(mapcar '+ py0 vec)
                        p2(mapcar '+ py1 vec)
                        distx(apply '+(mapcar '*(mapcar '- px1 py0)vecx))
                        vec(mapcar '(lambda(a)(* a distx))vecx)
                        p3(mapcar '+ py0 vec)
                        p4(mapcar '+ py1 vec)
                        ;;地表面データの範囲外の点は nil で返るので取り除いてから平均する
                        lst(vl-remove
                            nil
                            (project_to_ground
                             (list p1 p2 p3 p4)(list 0. 0. 1.)
                             (list str_lasground height_ground)))
                        )
                  ;;4点とも取れないときは動かさず、ブロック名を控えて先へ進む
                  (if(null lst)
                      (setq ls_skipblock(cons str_insertname ls_skipblock))
                    (progn
                      (setq zz(/(apply '+(mapcar 'caddr lst))(float(length lst)))
                            zz(- zz(caddr pz0))
                            p1(vlax-3d-point 0 0 0)
                            p2(vlax-3d-point 0 0 zz)
                            )
                      (vlax-for obj vnam_insert (vla-move obj p1 p2))))
                  ))
             )

           )

          ;;--- テンプレートから作った特殊部 / マンホール -------------------
          ;;  配置時の地表面標高との差だけブロックごと上下に動かす。
          ;;  土被り(マンホールは総高さ)はそのまま保たれる。CCBOXBLOCK と同じ考え方。
          ;;  基準の標高は 特殊部=GROUND-Z / マンホール=TOPZ(天端＝地表面)
          ((or(= str_type "CCBOXTEMPBLOCK")(= str_type "MANHOLEBLOCK"))
           ((lambda( / bool_mh num_old num_new num_len num_delta p_base vecx ls_pg lst)
              (setq bool_mh(= str_type "MANHOLEBLOCK")
                    num_old(cdr(assoc(if bool_mh "TOPZ" "GROUND-Z")ls_xdata))
                    num_len(cdr(assoc "LENGTH" ls_xdata))
                    vecx(list(cdr(assoc "VEC-X" ls_xdata))
                             (cdr(assoc "VEC-Y" ls_xdata))0.)
                    p_base(if bool_mh
                              (list(cdr(assoc "CENTER-X" ls_xdata))
                                   (cdr(assoc "CENTER-Y" ls_xdata))0.)
                            (list(cdr(assoc "BASE-X" ls_xdata))
                                 (cdr(assoc "BASE-Y" ls_xdata))0.))
                    str_insertname(vla-get-name vnam)
                    )
              (if(car vecx)T(setq vecx(list 1. 0. 0.)))
              (if num_len T(setq num_len 0.))

              (cond
               ;;この改訂より前に置いたものは基準の標高が無いので動かせない
               ((or(null num_old)(null(car p_base)))
                (setq ls_skipblock(cons str_insertname ls_skipblock)))
               (T
                ;;地表面標高 : 特殊部は配置時と同じく軸上11点の平均、マンホールは中心1点
                (setq ls_pg
                      (if bool_mh(list p_base)
                        (mapcar '(lambda(i)
                                   (mapcar '(lambda(a x)
                                              (+ a(*(-(* 0.1 i num_len)(* 0.5 num_len))x)))
                                           p_base vecx))
                                (inclist 0 11)))
                      lst(vl-remove
                          nil
                          (project_to_ground
                           ls_pg(list 0. 0. 1.)(list str_lasground height_ground)))
                      )
                (if(null lst)
                    (setq ls_skipblock(cons str_insertname ls_skipblock))
                  (progn
                    (setq num_new(/(apply '+(mapcar 'caddr lst))(float(length lst)))
                          num_delta(- num_new num_old)
                          vnam_insert(vla-Item
                                      (vla-get-Blocks
                                       (vla-get-ActiveDocument(vlax-get-acad-object)))
                                      str_insertname))
                    (if(<(abs num_delta)1e-8)T
                      (vlax-for obj vnam_insert
                                (vla-move obj(vlax-3d-point 0 0 0)
                                          (vlax-3d-point 0 0 num_delta))))

                    ;;動かした分だけ記録も更新する。並びは配置時のまま保つ
                    (set_xda
                     vnam
                     (apply
                      'append
                      (mapcar
                       '(lambda(a / str_key val)
                          (setq str_key(car a)val(cdr a))
                          (if(= str_key "terraduct3d")(list(cons 1000 val))
                            (progn
                              (setq val
                                    (cond
                                     ((= str_key "PROJECT-D")
                                      (if str_lasground str_lasground ""))
                                     ((= str_key "PROJECT-H")
                                      (if height_ground height_ground 0.))
                                     ((or(= str_key "GROUND-Z")(= str_key "TOPZ"))num_new)
                                     ((= str_key "BASE-Z")(+ val num_delta))
                                     (T val)))
                              (list(cons 1000 str_key)
                                   (cons(cond((=(type val)'STR)1000)
                                             ((=(type val)'INT)1071)
                                             (T 1040))
                                        val)))))
                       ls_xdata))
                     "terraduct3d")
                    ))))
              ))
           )
          )
           
           
           
         
         )

       ;;投影した経路(3Dポリライン・節点の円・円弧文字)を地表面へ載せ直す
       ;;  地表面データの範囲外の点は nil で返る。
       ;;  ポリラインは点数が変わると vla-put-coordinates が失敗するので、
       ;;  取れなかった点は元の位置のまま残す
       (mapcar
        '(lambda(vnam)
           (vlax-for
            obj vnam
            (cond
             ((=(vla-get-ObjectName obj)"AcDb3dPolyline")
              (setq ls_p(split_list 3(vlax-safearray->list(vlax-variant-value
                                                           (vla-get-coordinates obj))))
                    ls_pnew(project_to_ground
                            ls_p(list 0. 0. 1.)(list str_lasground height_ground))
                    )
              (if(/=(length ls_p)(length ls_pnew))T;;まったく投影できなかった
                (progn
                  (setq ls_p(apply 'append
                                   (mapcar '(lambda(p q)
                                              (if q q
                                                (progn
                                                  (setq int_outofground(1+ int_outofground))
                                                  p)))
                                           ls_p ls_pnew))
                        array_p(vlax-make-safearray vlax-vbDouble(cons 0(1-(length ls_p)))))
                  (vlax-safearray-fill array_p ls_p)
                  (vla-put-coordinates obj array_p)))
              )
             ((=(vla-get-ObjectName obj)"AcDbCircle")
              (setq p(vlax-safearray->list(vlax-variant-value(vla-get-center obj)))
                    p(car(project_to_ground
                          (list p)(list 0. 0. 1.)(list str_lasground height_ground)))
                    )
              (if p(vla-put-center obj(vlax-3d-point p))
                (setq int_outofground(1+ int_outofground)))
              )
             ((=(vla-get-ObjectName obj)"AcDbText")
              (setq p(vlax-safearray->list(vlax-variant-value
                                           (vla-get-TextAlignmentPoint obj)))
                    p(car(project_to_ground
                          (list p)(list 0. 0. 1.)(list str_lasground height_ground)))
                    )
              (if p(vla-put-insertionpoint obj(vlax-3d-point p))
                (setq int_outofground(1+ int_outofground)))
              )
             )
            )
           )
        ls_vnam_refreshproject)


       (setq int_selectmenu nil)
       (vla-Regen (vla-get-ActiveDocument (vlax-get-acad-object)) acAllViewports )

       ;;更新しました
       (x-alert
        (append
         (list 26356 26032 12375 12414 12375 12383)
         ;;\n地表面データの範囲外の点が n 個ありました(その点は動かしていません)
         (if(> int_outofground 0)
             (list "\n" 22320 34920 38754 12487 12540 12479 12398 31684 22258 22806 12398 28857 12364 " "
                   (itoa int_outofground) " " 20491 12354 12426 12414 12375 12383
                   "(" 12381 12398 28857 12399 21205 12363 12375 12390 12356 12414 12379 12435 ")")
           (list ))
         ;;\n更新できなかったブロック : …
         (if ls_skipblock
             (list "\n" 26356 26032 12391 12365 12394 12363 12387 12383 12502 12525 12483 12463 " : "
                   (vl-princ-to-string(reverse ls_skipblock)))
           (list ))
         ))

       (setq str_edit "home")
       ))
    
    
    )


   
   (list
    "profiledrawing" ;;edsym
    (cons
     "INITIAL"
     (lambda(bool);;initial
       (if(car bool)
           (progn
             ;;temp
             (setq bool_point nil
                   bool_selectent nil bool_select nil int_selectmode -1
                   ls_vnam_select nil
                   )

             (setq int_commandpage 0
                   ls_vnam_duct_draw(list)
                   vnam_plane_road nil
                   bool_select_plane_road nil
                   width_road_profile 20.
                   dist_new_number 10.
                   str_currentnumber ""
                   ratio_draw_verti 1. int_drawcircle 0
                   ls_drawprofile nil
                   space_drawing 10.
                   int_transdirection 0
                   )

             (setq ls_whole_duct(list)
                   set_ent(ssget "X"(list(cons 0 "INSERT")(list -3(list "terraduct3d"))))
                   num(if set_ent(sslength set_ent)0) )
             (while(>(setq num(1- num))-1)
               (setq vnam(vlax-ename->vla-object(ssname set_ent num)))
               (vla-getXData vnam "terraduct3d" 'array_Type 'array_Data )
               (if array_data
                   (setq ls_xdata
                         (split_list 0(mapcar 'vlax-variant-value
                                              (vlax-safearray->list array_data)))
                         str_type(cdr(assoc "terraduct3d" ls_xdata)))
                 (setq str_type nil) )

               (if(= str_type "DUCTBLOCK")
                   ((lambda( / str_obj vnam_center vnam_ground para_protect str_insertname)
                      
                      (setq str_insertname(vla-get-name vnam)
                            vnam(vla-Item(vla-get-Blocks(vla-get-ActiveDocument(vlax-get-acad-object)))
                                         str_insertname)
                            )
                      
                      (vlax-for
                       obj vnam
                       
                       (vla-getXData obj "terraduct3d" 'array_Type 'array_Data )
                       (if array_data
                           (setq ls_xdata
                                 (split_list 0(mapcar 'vlax-variant-value
                                                      (vlax-safearray->list array_data)))
                                 str_type(cdr(assoc "terraduct3d" ls_xdata)))
                         (setq str_type nil) )
                       
                       (cond
                        ((= str_type "CENTERLINE")
                         (setq ls_p(split_list 3(vlax-safearray->list
                                                 (vlax-variant-value
                                                  (vla-get-coordinates obj))))
                               ls_p(apply 'append(mapcar 'carxy ls_p))
                               vnam_ground(xvla-lwpoly ls_p(list nil nil :vlax-false))
                               )
                         
                         (setq obj
                               (vla-CopyObjects
                                (vla-get-ActiveDocument(vlax-get-acad-object))
                                (vlax-make-variant
                                 (vlax-safearray-fill
                                  (vlax-make-safearray vlax-vbObject (cons 0 0))
                                  (list obj)))
                                (vla-get-ModelSpace(vla-get-ActiveDocument(vlax-get-acad-object)))
                                )
                               vnam_center(car(vlax-safearray->list(vlax-variant-value obj)))
                               )
                         (mapcar '(lambda(vnam)
                                    (vla-put-visible vnam :vlax-false)
                                    (addkillobj vnam)
                                    )
                                 (list vnam_ground vnam_center))
                         
                         )
                        ((= str_type "DUCTSOLID")
                         (setq int_col(vla-get-color obj)
                               str_lay(vla-get-layer obj))
                         (setq diam_duct_temp(cdr(assoc "DIAM" ls_xdata)))
                         )
                        ((= str_type "CONMESH")
                         (setq para_protect
                               (mapcar '(lambda(str)(cons str(cdr(assoc str ls_xdata))))
                                       (list "CORNER" "WIDTH" "HEIGHT" "FILET")))
                         )
                        )
                       )
                      (setq ls_whole_duct
                            (cons(list vnam_ground vnam_center
                                       (append(list(cons "DIAM" diam_duct_temp)
                                                   (cons "COLOR" int_col)
                                                   (cons "LAYER" str_lay)
                                                   (cons "INSERTNAME" str_insertname)
                                                   )
                                              para_protect))
                                 ls_whole_duct)
                            )
                      )))
               )


             (setq
              func_guidemenu
              (lambda()
                (mix_strasc
                 (list (if ls_vnam_select(list 26377 12426)(list 28961 12375)) 12305
                       )
                 ) )
              
              ls_guideexplane
              (mapcar
               'mix_strasc
               (list
                ))
              
              ls_guidemenu
              (list
               
               ;; (list(list 69);;描画の対象とする管を選択
               ;;      (cons "ITEM"(list 25551 30011 12398 23550 35937 12392 12377 12427 31649 12434 36984 25246 ))
               ;;      (cons "LOADFUNCTION"
               ;;            (lambda()
                            
               ;;              nil
                            
                            
               ;;              ))

               ;;      (cons "STATUS"
               ;;            (lambda()
               ;;              (mix_strasc
               ;;               (if ls_vnam_duct_draw(list "{\\C" str_gcol_c ";" 36984 25246 28168 "}" )
               ;;                 (list "{\\C" str_gcol_g ";" 12377 12409 12390 "}" ))))
               ;;            )
               ;;      ;;選択されなかった管は描画されません\n何も選択していないとき、図面内のすべてを対象にします
               ;;      (cons "HELP"(lambda()(mix_strasc(list 36984 25246 12373 12428 12394 12363 12387 12383 31649 12399 25551 30011 12373 12428 12414 12379 12435 "\n" 20309 12418 36984 25246 12375 12390 12356 12394 12356 12392 12365 12289 22259 38754 20869 12398 12377 12409 12390 12434 23550 35937 12395 12375 12414 12377 ))))
               ;;      )
               
               (list(list 65);;平面線形を選択
                    (cons "ITEM"(list 24179 38754 32218 24418 12434 36984 25246 ))
                    (cons "LOADFUNCTION"
                          (lambda()
                            (setq vnam_plane_road nil
                                  bool_select_plane_road T

                                  bool_point nil 
                                  bool_selectent T bool_select T int_selectmode 0
                                  ls_ssget(list(cons -4 "<OR")
                                               (cons 0 "LINE,LWPOLYLINE,POLYLINE,ARC")
                                               ;; (cons -4 "<AND")
                                               ;; (cons 0 "INSERT")(list -3(list "terraduct3d"))
                                               ;; (cons -4 "AND>")
                                               (cons -4 "OR>")
                                               )
                                  
                                  ls_ssgetinsert(list(cons 0 "INSERT")
                                                     (cons -4 "<NOT")(list -3(list "terraduct3d"))(cons -4 "NOT>") )
                                  xtype_ssget nil xdata_ssget nil
                                  
                                  int_selectmenu_temp
                                  ((lambda( lst ii / num)
                                     (setq num 0)
                                     (while lst
                                       (if(=(caaar lst)ii)(setq lst nil)
                                         (setq num(1+ num)lst(cdr lst)))
                                       )
                                     num)
                                   ls_guidemenu_page 82)
                                  )
                            ))
                    (cons "STATUS"
                          (lambda()
                            (mix_strasc
                             (if(= int_selectmenu
                                   ((lambda( lst ii / num)
                                      (setq num 0)
                                      (while lst
                                        (if(=(caaar lst)ii)(setq lst nil)
                                          (setq num(1+ num)lst(cdr lst)))
                                        )
                                      num)
                                    ls_guidemenu_page 82))
                                 ;;bool_select_plane_road
                                 (list "{\\C" str_gcol_y ";" 36984 25246 12375 12390 12367 12384 12373 12356  "}")
                               (if vnam_plane_road
                                   (list "{\\C" str_gcol_c ";" 36984 25246 28168 "}" )
                                 (list "{\\C" str_gcol_p ";" 26410 36984 25246 "}" ))))))

                    ;; (cons "SELECTCANCEL"
                    ;;       (lambda()
                    ;;         (if(= int_selectmenu
                    ;;               ((lambda( lst ii / num)
                    ;;                  (setq num 0)
                    ;;                  (while lst
                    ;;                    (if(=(caaar lst)ii)(setq lst nil)
                    ;;                      (setq num(1+ num)lst(cdr lst)))
                    ;;                    )
                    ;;                  num)
                    ;;                ls_guidemenu_page 82))
                    ;;             T
                    ;;           (setq bool_select_plane_road nil
                    ;;                 int_commandpage 0
                    ;;                 func_selectcansel nil
                    ;;                 ))
                    ;;         ))
                    
                    
                    (cons "HELP"(lambda()(mix_strasc(list))))
                    )

               
               (list(list 78);;編集中の横断の名称 -page
                    (cons "ITEM"(list 32232 38598 20013 12398 27178 26029 12398 21517 31216 ))
                    (list "PAGE" 1)
                    (cons "INPUTSTR"
                          (lambda( / str i bool func) 'str_currentnumber) )
                    (cons "NO-INPUT" (lambda()nil ))
                    (cons "LOADFUNCTION"
                          (lambda(str / bool)
                            (if(vl-position
                                str(mapcar '(lambda(a)(cdr(assoc "NUMBER" a)))
                                           (vl-remove ls_current ls_vnam_number)))
                                nil
                              (progn
                                (setq str_currentnumber str)
                                (func_road_number
                                 (subst(cons "NUMBER" str)
                                       (assoc "NUMBER" ls_current)ls_current))
                                (save_road_number)
                                T
                                )
                              )
                            
                            )
                          )
                    
                    (cons "STRINPUTALERT";;横断名称が存在しています
                          (mix_strasc(list 27178 26029 21517 31216 12364 23384 22312 12375 12390 12356 12414 12377  ))
                          )
                    
                    (cons "HELP"(lambda()(mix_strasc(list  ))))
                    )
               
               (list(list 87);;編集中の横断の幅 -page
                    (cons "ITEM"(list 32232 38598 20013 12398 27178 26029 12398 24133 ))
                    (list "PAGE" 1)
                    (cons "INPUT"(lambda() 'width_road_profile))
                    (cons "LOADFUNCTION"
                          (lambda()
                            (if ls_current
                                (if(<(abs width_road_profile)1e-8)
                                    (alert(mix_strasc(list "0" 12399 20837 21147 12391 12365 12414 12379 12435 )))
                                  (progn
                                    (func_road_number
                                     (subst(cons "WIDTH" width_road_profile)
                                           (assoc "WIDTH" ls_current)ls_current))
                                    (save_road_number)
                                    )
                                  )
                              )
                            
                            ))
                    (cons "HELP"(lambda()(mix_strasc(list(if int_selectmenu str_guide_inputval str_guide_selectval) ))))
                    )
               
               (list(list 68);;編集中の横断からの距離を指定 -page
                    (cons "ITEM"(list 32232 38598 20013 12398 27178 26029 12363 12425 12398 36317 38626 12434 25351 23450 ))
                    (list "PAGE" 1)
                    (cons "INPUT"(lambda() 'dist_new_number))
                    (cons "LOADFUNCTION"
                          (lambda( / dd)
                            (if ls_current
                                (if(<(abs dist_new_number)1e-8)
                                    (alert(mix_strasc(list "0" 12399 20837 21147 12391 12365 12414 12379 12435 )))
                                  (progn
                                    (setq dd(cdr(assoc "DIST" ls_current))
                                          ls_vnam_number
                                          (cons(func_road_number
                                                (list(cons "DIST"(+ dd dist_new_number))
                                                     (assoc "WIDTH" ls_current)))
                                               ls_vnam_number)
                                          ls_current(car ls_vnam_number)
                                          str_currentnumber(cdr(assoc "NUMBER" ls_current))
                                          )
                                    (save_road_number)
                                    )
                                  )
                              ;;横断選択時に使用可能です
                              (alert(mix_strasc(list 27178 26029 36984 25246 26178 12395 20351 29992 21487 33021 12391 12377 )))
                              )
                            ))
                    
                    (cons "HELP"(lambda()(mix_strasc(list(if int_selectmenu str_guide_inputval str_guide_selectval) ))))
                    )
               
               (list(list 82) ;; 横断方向-page
                    (cons "ITEM"(list 27178 26029 26041 21521  ))
                    (list "PAGE" 1)
                    (cons "INPUTSWITCH"
                          (lambda()
                            (list 'int_transdirection
                                  (mapcar 'mix_strasc
                                          (list(list "{\\C" str_gcol_g ";" 27491  "}")
                                               (list "{\\C" str_gcol_c ";" 21453 36578  "}")))
                                  ))
                          )
                    (cons "LOADFUNCTION"
                          (lambda( / dd)
                            (mapcar '(lambda(lst)(func_road_number lst))ls_vnam_number)
                            ))
                    )
               
               (list(list 88) ;;編集中の横断を削除 -page
                    (cons "ITEM"(list 32232 38598 20013 12398 27178 26029 12434 21066 38500 ))
                    (list "PAGE" 1)
                    (cons "LOADFUNCTION"
                          (lambda( / dd)
                            (if ls_current
                                (progn
                                  (mapcar '(lambda(str / vnam)
                                             (setq vnam(cdr(assoc str ls_current)))
                                             (exckillobj vnam)
                                             (vla-delete vnam)
                                             )
                                          (list "LINE" "TEXT0" "TEXT1"))
                                  (setq ls_vnam_number
                                        (vl-remove ls_current ls_vnam_number)
                                        ls_current nil
                                        str_currentnumber nil
                                        )
                                  (save_road_number)
                                  
                                  )
                              ;;横断選択時に使用可能です
                              (alert(mix_strasc(list 27178 26029 36984 25246 26178 12395 20351 29992 21487 33021 12391 12377 )))
                              )
                            ))
                    )
               
               (list(list 49) ;;横断作成 -DCL
                    (cons "ITEM"(list 27178 26029 20316 25104 ))
                    (list "PAGE" 1)
                    (cons
                     "LOADFUNCTION"
                     (lambda( / ls_roaddata bool_loop)
                       (if ls_vnam_number
                           (progn
                             (setq ls_roaddata
                                   (mapcar
                                    '(lambda(lst / str dd ww)
                                       (setq str(cdr(assoc "NUMBER" lst))
                                             dd(cdr(assoc "DIST" lst))
                                             ww(cdr(assoc "WIDTH" lst))
                                             )
                                       (list dd str ww)
                                       )
                                    ls_vnam_number)
                                   ls_roaddata(vl-sort ls_roaddata '(lambda(a b)(<(car a)(car b))))
                                   
                                   )

                             
                             (setq path_drawtransdcl(strcat str_path_tempdirectory "drawtrans.dcl") 
                                   open_file (open path_drawtransdcl "w")
                                   )

                             (write_strlist
                              open_file
                              (list
                               "Sedit :dialog"
                               "{"
                               (mix_strasc;;横断出力
                                (list " label = \""  27178 26029 20986 21147  "\";"))

                               (list_to_dcltext;;断面図鉛直倍率
                                (list "edit_box"(cons "width" "20")(cons "fixed_width" "true")
                                      (cons "label"(mix_strasc(list 26029 38754 22259 37467 30452 20493 29575  )))
                                      (cons "key" "drawverti")))

                               (list_to_dcltext;;※水平：1に対する倍率
                                (list "text"(cons "width" "20")(cons "fixed_width" "true")
                                      (cons "value"(mix_strasc(list 8251 27700 24179 65306 "1" 12395 23550 12377 12427 20493 29575  )))
                                      ))
                               
                               (list_to_dcltext;;管の断面形状
                                (list "popup_list"(cons "width" "20")(cons "fixed_width" "true")
                                      (cons "label"(mix_strasc(list 26029 38754 22259 37467 30452 20493 29575 )))
                                      (cons "key" "drawcircle")))

                               (list_to_dcltext;;記載ピッチ
                                (list "edit_box"(cons "width" "20")(cons "fixed_width" "true")
                                      (cons "label"(mix_strasc(list 35352 36617 12500 12483 12481  )))
                                      (cons "key" "drawpitch")))
                               
                               (list_to_dcltext;;出力する横断の名称と幅を指定してください
                                (list "text"(cons "width" "50")(cons "fixed_width" "true")
                                      (cons "value"(mix_strasc(list 20986 21147 12377 12427 27178 26029 12398 21517 31216 12392 24133 12434 25351 23450 12375 12390 12367 12384 12373 12356  )))))
                               
                               " :row"
                               " {"
                               "  alignment = left;"
                               "  fixed_width = true;"
                               (list_to_dcltext;;すべて出力
                                (list "button"(cons "width" "16")(cons "fixed_width" "true")
                                      (cons "label"(mix_strasc(list 12377 12409 12390 20986 21147 )))(cons "key" "allselecton")))
                               (list_to_dcltext;;すべて解除
                                (list "button"(cons "width" "16")(cons "fixed_width" "true")
                                      (cons "label"(mix_strasc(list 12377 12409 12390 35299 38500 )))(cons "key" "allselectoff")))
                               "  }"

                               
                               " :row"
                               " {"
                               "  alignment = left;"
                               "  fixed_width = true;"
                               
                               (mapcar
                                '(lambda(ls_data)
                                   (list
                                    " :column"
                                    " {"
                                    "  alignment = top;"
                                    "  fixed_height = true;"
                                    (mapcar
                                     '(lambda(lst / str ww)
                                        (setq str(car lst)ww(cadr lst))
                                        (list
                                         " :row"
                                         " {"
                                         "  alignment = left;"
                                         "  fixed_width = true;"
                                         
                                         (list_to_dcltext
                                          (list "toggle"(cons "width" "10")(cons "fixed_width" "true")
                                                (cons "label" str)(cons "value" "1")
                                                (cons "key"(strcat "profile-" str))))
                                         (list_to_dcltext
                                          (list "edit_box"(cons "width" "10")(cons "fixed_width" "true")
                                                (cons "value"(rtos ww 2 3))
                                                (cons "key"(strcat "width-" str))))
                                         "  }"
                                         
                                         )
                                        )
                                     ls_data)
                                    "  }"
                                    ))
                                (mapcar '(lambda(lst)(vl-remove nil lst))
                                           (split_list 10(mapcar 'cdr ls_roaddata)))
                                )
                               
                               "  }"
                               " ok_cancel;"
                               (list_to_dcltext;;※OKを押した後、描画位置をクリックしてください
                                (list "text"(cons "width" "40")(cons "fixed_width" "true")
                                      (cons "value"(mix_strasc(list 8251 "OK" 12434 25276 12375 12383 24460 12289 25551 30011 20301 32622 12434 12463 12522 12483 12463 12375 12390 12367 12384 12373 12356 )))
                                      ))
                               
                               " }";//end
                               )
                              )
                             
                             (close open_file)
                             
                             (setq button_select_drawtrans
                                   (lambda(bool / str_toggle)
                                     (setq str_toggle(if bool "1" "0"))
                                     
                                     (mapcar
                                      '(lambda(lst / str)
                                         (set_tile(strcat "profile-"(cadr lst))str_toggle))
                                      ls_roaddata)
                                     )
                                   
                                   accept_drawtrans
                                   (lambda( / )
                                     (setq ratio_drawverti(atof(get_tile "drawverti"))
                                           pitch_draw(atof(get_tile "drawpitch"))
                                           type_drawcircle(get_tile "drawcircle")
                                           )
                                     (setq ls_profiletrans(list))
                                     (mapcar
                                      '(lambda(lst / str ww)
                                         (setq str(cadr lst))
                                         (if(=(get_tile(strcat "profile-" str))"1")
                                             (setq ls_profiletrans
                                                   (cons(list str(atof(get_tile(strcat "width-" str))))
                                                        ls_profiletrans)
                                                   )))
                                      ls_roaddata)
                                     
                                     (if(< ratio_drawverti 1e-8);;縦断倍率が小さすぎます
                                         (alert(mix_strasc(list 32294 26029 20493 29575 12364 23567 12373 12377 12366 12414 12377 )))
                                       (if(< pitch_draw 1e-8);;ピッチが小さすぎます
                                           (alert(mix_strasc(list 12500 12483 12481 12364 23567 12373 12377 12366 12414 12377 )))
                                         (done_dialog 1)))
                                     
                                     )
                                   )
                             (setq bool_loop T)

                             
                             (while bool_loop
                               (setq load_dcl (load_dialog path_drawtransdcl))
                               (new_dialog "Sedit" load_dcl)

                               (set_tile "drawverti" "1.0")
                               (set_tile "drawpitch" "0.5")
                               (start_list "drawcircle");;傾斜を考慮して楕円,中心を合わせて正円
                               (mapcar '(lambda(lst)(add_list(mix_strasc lst)))
                                       (list(list 20670 26012 12434 32771 24942 12375 12390 26965 20870 )
                                            (list 20013 24515 12434 21512 12431 12379 12390 27491 20870 )))
                               (end_list)
                               
                               (action_tile "allselecton" "(button_select_drawtrans T)")
                               (action_tile "allselectoff" "(button_select_drawtrans nil)")
                               (action_tile "accept" "(accept_drawtrans)")
                               
                               (setq dialog-box (start_dialog))
                               (unload_dialog load_dcl)
                               
                               (if(<(getvar "DIASTAT")2)(setq bool_loop nil))
                               )

                             (setq ls_drawprofile
                                   (mapcar
                                    '(lambda(lst / str ww ls_ground str_name)
                                       
                                       (setq str_name(car lst)ww(cadr lst)
                                             lst((lambda(lst / ls_out)
                                                   (while lst
                                                     (setq ls_out(car lst))
                                                     (if(vl-position(cons "NUMBER" str_name)ls_out)
                                                         (setq lst nil)
                                                       (setq lst(cdr lst)ls_out nil))
                                                     )
                                                   ls_out
                                                   )
                                                 ls_vnam_number)
                                             )
                                       
                                       (setq vnam_line(cdr(assoc "LINE" lst))
                                             p0(vlax-curve-getstartpoint vnam_line)
                                             p1(vlax-curve-getendpoint vnam_line)
                                             vec_line(unit_vector(mapcar '- p1 p0))
                                             vec_normal(list(cadr vec_line)(-(car vec_line))0.)
                                             pc(mapcar '(lambda(a b)(* 0.5(+ a b)))p0 p1)
                                             )
                                       (if(=(setq ww2(cdr(assoc "WIDTH" lst)))ww)T
                                         (progn
                                           (setq p0(mapcar '(lambda(a b)(+ a(* -0.5 ww2)b))pc vec_line)
                                                 p1(mapcar '(lambda(a b)(+ a(*  0.5 ww2)b))pc vec_line)
                                                 )
                                           (vla-put-startpoint vnam_line(vlax-3d-point p0))
                                           (vla-put-endpoint vnam_line(vlax-3d-point p1))
                                           ))

                                       (setq dd(distance p0 p1)nn(1+(fix(/ dd pitch_draw)))
                                             dd(/ dd nn)
                                             ls_ground
                                             (project_to_ground
                                              (mapcar '(lambda(i)
                                                         (mapcar '(lambda(a b)(+ a(* i dd b)))p0 vec_line))
                                                      (inclist 0(1+ nn)))
                                              (list 0. 0. 1.)(list str_lasground height_ground)
                                              )
                                             ls_ground(vl-remove nil ls_ground)
                                             
                                             ls_ground
                                             (mapcar '(lambda(p / xx zz )
                                                        (setq zz(*(caddr p)ratio_drawverti)
                                                              xx(apply '+(mapcar '(lambda(a b c)(*(- a b)c))
                                                                                 p pc vec_line))
                                                              )
                                                        (list xx zz))
                                                     ls_ground)
                                             
                                             xmin(caar ls_ground)xmax(car(last ls_ground))
                                             ymin(apply 'min(mapcar 'cadr ls_ground))
                                             ymax(apply 'max(mapcar 'cadr ls_ground))
                                             
                                             )

                                       
                                       (setq ls_cross_duct(list))
                                       (mapcar
                                        '(lambda(lst / vnam_ground vnam_center ls_para px)
                                           (setq vnam_ground(car lst)
                                                 vnam_center(cadr lst)
                                                 ls_para(caddr lst)
                                                 rr(* 0.5(cdr(assoc "DIAM" ls_para)))
                                                 )
                                           (vla-put-elevation vnam_ground elev_road)

                                           (if(setq px(car(get_inters_point_vna
                                                           vnam_line vnam_ground 00)))
                                               (progn
                                                 (vla-put-startpoint vnam_cross_temp(vlax-3d-point px))
                                                 (vla-put-endpoint
                                                  vnam_cross_temp(vlax-3d-point(mapcar '+ px(list 0. 0. 1.))))
                                                 (setq px(car(get_inters_point_vna
                                                              vnam_cross_temp vnam_center 10))
                                                       zz(*(caddr px)ratio_drawverti)

                                                       xx(apply '+(mapcar '(lambda(a b c)(*(- a b)c))
                                                                          px pc vec_line))
                                                       )
                                                 
                                                 (if(= type_drawcircle "1")
                                                     (setq vec_ell(list 0. rr 0.) ratio_ell 1.


                                                           )
                                                   (progn
                                                     (setq vec(xvla-normal vnam_center px)
                                                           vec(trans-x vec(list 0 0 1)vec_normal)
                                                           vec_ell(carxyz vec 0.)
                                                           dd(distance(list 0. 0. 0.)vec_ell)
                                                           ratio_ell(sqrt(- 1.(expt dd 2)))
                                                           vec_ell(mapcar '(lambda(a)
                                                                             (/(* a rr)(* dd ratio_ell)))
                                                                          vec_ell)
                                                           )
                                                     (if(<(cadr vec_ell)0.)
                                                         (setq vec_ell(mapcar '- vec_ell)))
                                                     
                                                     (if(= ratio_drawverti 1.)
                                                         T
                                                       ((lambda( / aa bb cc ao bo co dd)
                                                          (setq ao rr
                                                                bo(distance(list 0. 0. 0.)vec_ell)
                                                                co(atan(cadr vec_ell)(car vec_ell))
                                                                )
                                                          (setq aa(+(expt(/(cos co)ao)2)
                                                                    (expt(/(sin co)bo)2))
                                                                bb(* 2.(sin co)(cos co)
                                                                     (+(/ 1. ao)(/ 1. bo))
                                                                     (-(/ 1. ao)(/ 1. bo)))
                                                                cc(+(expt(/(sin co)ao)2)
                                                                    (expt(/(cos co)bo)2))
                                                                )

                                                          (setq bb(/ bb ratio_drawverti)
                                                                cc(/ cc ratio_drawverti ratio_drawverti)
                                                                )

                                                          (setq co(* 0.5(atan bb(- aa cc)))
                                                                dd(sqrt(+(expt(- aa cc)2)(expt bb 2)))
                                                                ao(* 0.5(+ aa cc dd))
                                                                bo(* 0.5(+ aa cc(- dd)))
                                                                ao(/ 1.(sqrt ao))bo(/ 1.(sqrt bo))
                                                                )

                                                          (setq vec_ell
                                                                (list(*(cos co)ao)(*(sin co)ao)0.)
                                                                ratio_ell(/ bo ao)
                                                                )

                                                          
                                                          )))
                                                     ))

                                                 (if(> ratio_ell 1.)
                                                     (progn
                                                       (setq vec_ell(mapcar '(lambda(a)( * a ratio_ell))
                                                                            (list(cadr vec_ell)(-(car vec_ell))0.)))
                                                       (if(<(cadr vec_ell)0.)
                                                           (setq vec_ell(mapcar '- vec_ell)))
                                                       (setq ratio_ell(/ 1. ratio_ell))
                                                       ))

                                                 (setq ls_cross_duct
                                                       (cons(list xx zz vec_ell ratio_ell ls_para)
                                                            ls_cross_duct)
                                                       )

                                                 (if xmin 
                                                     (setq xmin(min xmin xx)xmax(max xmax xx)
                                                           ymin(min ymin zz)ymax(max ymax zz))
                                                   (setq xmin xx xmax xx ymin zz ymax zz)
                                                   )
                                                 
                                                 ))
                                           )
                                        ls_whole_duct)
                                       
                                       (setq dist_basedraw(* 10. ratio_drawverti))
                                       
                                       (setq y_dl0(/ ymin dist_basedraw)
                                             base_height(*(-(fix y_dl0)(if(< y_dl0 0.)1 0))10)
                                             y_dl0(* base_height ratio_drawverti)
                                             y_dl1(/ ymax dist_basedraw)
                                             y_dl1(*(+(fix y_dl1)(if(< y_dl1 0.)0 1))dist_basedraw)
                                             )
                                       
                                       (list str_name xmin xmax y_dl0(- y_dl1 y_dl0)
                                             (itoa base_height) ls_ground(list 0 ls_cross_duct))
                                       
                                       )
                                    ls_profiletrans)
                                   ls_drawprofile(vl-remove-if '(lambda(a)(null(cadr a)))ls_drawprofile)
                                   )
                             (setq xmin(apply 'min(mapcar 'cadr ls_drawprofile))
                                   xmax(apply 'max(mapcar 'caddr ls_drawprofile))
                                   width_area(+(- xmax xmin)space_drawing)
                                   height_area(apply '+(mapcar '(lambda(lst) (+(nth 4 lst)space_drawing))
                                                               ls_drawprofile))
                                   ls_drawprofile(reverse ls_drawprofile)
                                   )
                             ;;配置を指定してください
                             (x-alert(list 37197 32622 12434 25351 23450 12375 12390 12367 12384 12373 12356  ))
                             
                             
                             )
                         ;;横断の設定がありません
                         (x-alert(list 27178 26029 12398 35373 23450 12364 12354 12426 12414 12379 12435 ))
                         )
                       
                       )
                     )
                    )

               (list(list 50) ;;縦断作成 -DCL
                    (cons "ITEM"(list 32294 26029 20316 25104 ))
                    (list "PAGE" 1)
                    (cons "LOADFUNCTION"
                          (lambda( / bool_loop)

                            ;; (if ls_vnam_number
                            ;;     (progn
                            ;;       (setq ls_roaddata
                            ;;             (mapcar
                            ;;              '(lambda(lst / str dd ww)
                            ;;                 (setq str(cdr(assoc "NUMBER" lst))
                            ;;                       dd(cdr(assoc "DIST" lst))
                            ;;                       ww(cdr(assoc "WIDTH" lst))
                            ;;                       )
                            ;;                 (list dd str ww)
                            ;;                 )
                            ;;              ls_vnam_number)
                            ;;             ls_roaddata(vl-sort ls_roaddata '(lambda(a b)(<(car a)(car b))))
                                        
                            ;;             )
                            
                            (setq path_drawroaddcl(strcat str_path_tempdirectory "drawroad.dcl") 
                                  open_file (open path_drawroaddcl "w")
                                  )
                            
                            (write_strlist
                             open_file
                             (list
                              "Sedit :dialog"
                              "{"
                              (mix_strasc;;縦断出力
                               (list " label = \""  20986 21147  "\";"))

                              (list_to_dcltext;;断面図鉛直倍率
                               (list "edit_box"(cons "width" "20")(cons "fixed_width" "true")
                                     (cons "label"(mix_strasc(list 26029 38754 22259 37467 30452 20493 29575  )))
                                     (cons "key" "drawverti")))

                              (list_to_dcltext;;※水平：1に対する倍率
                               (list "text"(cons "width" "20")(cons "fixed_width" "true")
                                     (cons "value"(mix_strasc(list 8251 27700 24179 65306 "1" 12395 23550 12377 12427 20493 29575  )))
                                     ))
                              

                              (list_to_dcltext;;記載ピッチ
                               (list "edit_box"(cons "width" "20")(cons "fixed_width" "true")
                                     (cons "label"(mix_strasc(list 35352 36617 12500 12483 12481  )))
                                     (cons "key" "drawpitch")))

                              (list_to_dcltext;;縦断起点
                               (list "popup_list"(cons "width" "20")(cons "fixed_width" "true")
                                     (cons "label"(mix_strasc(list  )))
                                     (cons "key" "drawstart")))
                              (list_to_dcltext;;縦断終点
                               (list "popup_list"(cons "width" "20")(cons "fixed_width" "true")
                                     (cons "label"(mix_strasc(list  )))
                                     (cons "key" "drawend")))
                              
                              
                              " ok_cancel;"
                              (list_to_dcltext;;※OKを押した後、描画位置をクリックしてください
                               (list "text"(cons "width" "40")(cons "fixed_width" "true")
                                     (cons "value"(mix_strasc(list 8251 "OK" 12434 25276 12375 12383 24460 12289 25551 30011 20301 32622 12434 12463 12522 12483 12463 12375 12390 12367 12384 12373 12356 )))
                                     ))
                              
                              " }";//end
                              )
                             )
                             
                            (close open_file)

                            (setq accept_drawroad
                                  (lambda( / )
                                    (setq ratio_drawverti(atof(get_tile "drawverti"))
                                          pitch_draw(atof(get_tile "drawpitch"))
                                          int_start(atoi(get_tile "drawstart"))
                                          int_end(atoi(get_tile "drawend"))
                                          )
                                    
                                    (if(< ratio_drawverti 1e-8);;縦断倍率が小さすぎます
                                        (alert(mix_strasc(list 32294 26029 20493 29575 12364 23567 12373 12377 12366 12414 12377 )))
                                      (if(< pitch_draw 1e-8);;ピッチが小さすぎます
                                          (alert(mix_strasc(list 12500 12483 12481 12364 23567 12373 12377 12366 12414 12377 )))
                                        (done_dialog 1)))
                                    
                                    )
                                  )
                            
                            (setq bool_loop T)
                            (setq ls_vnam_number
                                  (vl-sort ls_vnam_number
                                           '(lambda(a b)(<(cdr(assoc "DIST" a))(cdr(assoc "DIST" b)))))
                                  ls_cross_number
                                  (mapcar '(lambda(lst / str vnam dd pp)
                                             (list(cdr(assoc "NUMBER" lst))
                                                  (cdr(assoc "DIST" lst))
                                                  )
                                             )
                                          ls_vnam_number)
                                  )
                            
                            (while bool_loop
                              (setq load_dcl (load_dialog path_drawroaddcl))
                              (new_dialog "Sedit" load_dcl)

                              (set_tile "drawverti" "1.0")
                              (set_tile "drawpitch" "0.5")

                              (start_list "drawstart");;線形の端点
                              (add_list(mix_strasc(list 32218 24418 12398 31471 28857 )))
                              (mapcar '(lambda(lst)(add_list(car lst)))ls_cross_number)
                              (end_list)
                              (start_list "drawend");;線形の端点
                              (add_list(mix_strasc(list 32218 24418 12398 31471 28857 )))
                              (mapcar '(lambda(lst)(add_list(car lst)))ls_cross_number)
                              (end_list)

                              (action_tile "accept" "(accept_drawroad)")
                              
                              (setq dialog-box (start_dialog))
                              (unload_dialog load_dcl)
                              
                              (if(<(getvar "DIASTAT")2)(setq bool_loop nil))
                              )
                            
                            (setq dist_start
                                  (if(= int_start 0)0.(cadr(nth(1- int_start)ls_cross_number)))
                                  dist_end
                                  (if(= int_start 0)
                                      (vlax-curve-getdistatparam
                                       vnam_plane_road
                                       (vlax-curve-getendparam vnam_plane_road))
                                    (cadr(nth(1- int_end)ls_cross_number)))
                                  )
                            
                            (setq dd(- dist_end dist_start)nn(1+(fix(/ dd pitch_draw)))
                                  bool_direction(> dd 0) dd(/ dd nn)
                                  ls_distpoint
                                  (mapcar '(lambda(i / x p d)
                                             (setq d(* i dd)x(+ d dist_start)
                                                   p(vlax-curve-getpointatdist
                                                     vnam_plane_road x))
                                             (if p (list(abs d)p
                                                        ((lambda( / v)
                                                           (setq v(xvla-normal vnam_plane_road p))
                                                           (list(cadr v)(-(car v))0.)))
                                                        )))
                                          (inclist 0(1+ nn)))
                                  ls_ground(vl-remove nil ls_ground)
                                  
                                  ls_ground
                                  (project_to_ground
                                   (mapcar 'cadr ls_distpoint)
                                   (list 0. 0. 1.)(list str_lasground height_ground)
                                   )
                                  
                                  ls_ground(vl-remove nil(mapcar '(lambda(a b)(if b(list(car a)b)))
                                                                 ls_distpoint ls_ground))
                                  
                                  ls_ground
                                  (mapcar '(lambda(p / xx zz )
                                             (setq zz(*(caddr(cadr p))ratio_drawverti)
                                                   xx(car p) )
                                             (list xx zz))
                                          ls_ground)
                                  xmin(caar ls_ground)xmax(car(last ls_ground))
                                  ymin(apply 'min(mapcar 'cadr ls_ground))
                                  ymax(apply 'max(mapcar 'cadr ls_ground))
                                  )

                            (setq ls_project_duct(list))
                            (mapcar
                             '(lambda(lst / pp vec ls_p)
                                (setq pp(cadr lst)vec(caddr lst) )
                                (vla-put-startpoint
                                 vnam_cross_temp(vlax-3d-point pp))
                                (vla-put-endpoint
                                 vnam_cross_temp(vlax-3d-point(mapcar '+ pp vec)))
                                (setq ls_p(mapcar
                                           '(lambda(lst / vnam_ground vnam_center ls_para px)
                                              (setq vnam_ground(car lst)
                                                    ;; vnam_center(cadr lst)
                                                    ;; ls_para(caddr lst)
                                                    ;; rr(* 0.5(cdr(assoc "DIAM" ls_para)))
                                                    )
                                              (vla-put-elevation vnam_ground elev_road)
                                              
                                              (setq px(car(get_inters_point_vna
                                                           vnam_cross_temp vnam_ground 10))
                                                    )
                                              
                                              px
                                              )
                                           ls_whole_duct)
                                      ls_project_duct
                                      (if ls_project_duct
                                          (mapcar '(lambda(a b)(cons a b))ls_p ls_project_duct)
                                        (mapcar '(lambda(a)(list a))ls_p))
                                      )
                                
                                )
                             ls_distpoint)

                            
                            (setq ls_project_duct
                                  (mapcar
                                   '(lambda(lst ls_px / vnam_center ls_para)
                                      (if(apply 'or ls_px)
                                          (progn
                                            (setq vnam_center(cadr lst)
                                                  ls_para(caddr lst)
                                                  ls_px(reverse ls_px)
                                                  )

                                            
                                            (setq lst(mapcar
                                                      '(lambda(px ls_dist / dd zz)
                                                         (setq dd(car ls_dist))
                                                         (if px
                                                             (progn
                                                               (vla-put-startpoint
                                                                vnam_cross_temp
                                                                (vlax-3d-point px))
                                                               (vla-put-endpoint
                                                                vnam_cross_temp
                                                                (vlax-3d-point
                                                                 (mapcar '+ px(list 0. 0. 1.))))
                                                               (setq px(car(get_inters_point_vna
                                                                            vnam_cross_temp vnam_center 10))
                                                                     zz(caddr px)
                                                                     ymin(min ymin(* zz ratio_drawverti))
                                                                     ymax(max ymax(* zz ratio_drawverti))
                                                                     )
                                                               
                                                               (list(car ls_dist)zz)
                                                               ))
                                                         )
                                                      ls_px ls_distpoint)
                                                  )
                                            (list(vl-remove nil lst)ls_para)
                                            ))
                                      )
                                   ls_whole_duct ls_project_duct)
                                  ls_project_duct(vl-remove nil ls_project_duct)
                                  )
                            
                            (setq dist_basedraw(* 10. ratio_drawverti))
                            
                            (setq y_dl0(/ ymin dist_basedraw)
                                  base_height(*(-(fix y_dl0)(if(< y_dl0 0.)1 0))10)
                                  y_dl0(* base_height ratio_drawverti)
                                  y_dl1(/ ymax dist_basedraw)
                                  y_dl1(*(+(fix y_dl1)(if(< y_dl1 0.)0 1))dist_basedraw)
                                  )

                            (setq ls_drawprofile
                                  (list(list(mix_strasc(list 32294 26029 22259))
                                            xmin xmax y_dl0(- y_dl1 y_dl0)
                                            (itoa base_height) ls_ground(list 1 ls_project_duct))
                                       )
                                  )
                            (princ(list 8 9))
                            
                            (setq width_area(+(- xmax xmin)space_drawing)
                                  height_area(apply '+(mapcar '(lambda(lst) (+(cadddr lst)space_drawing))
                                                              ls_drawprofile))
                                  )
                            
                            ;;配置を指定してください
                            (x-alert(list 37197 32622 12434 25351 23450 12375 12390 12367 12384 12373 12356  ))
                            
                            )
                          )
                    )

               

               
               (list(list 67);;クロソイド作成
                    (cons "ITEM"(list 12463 12525 12477 12452 12489 20316 25104 ))
                    (list "PAGE" 0)
                    (cons "NEXTMODE" "senkeidraw");;
                    ;;交差する2直線を指定し、それをつなぐクロソイドを描画します
                    (cons "HELP"(lambda()(mix_strasc(list 20132 24046 12377 12427 "2" 30452 32218 12434 25351 23450 12375 12289 12381 12428 12434 12388 12394 12368 12463 12525 12477 12452 12489 12434 25551 30011 12375 12414 12377 ))))
                    )

               (list(list 80);;選択モード切替
                    (cons "ITEM"(list 36984 25246 12514 12540 12489 20999 26367))
                    (list "PAGE" 2)
                    (cons "INPUTSWITCH"
                          (lambda()
                            (if(= int_selectmode -1)
                                (list nil(mix_strasc
                                          (list "{\\C" str_gcol_p ";"
                                                21336 20307 36984 25246 12398 12415 "}")))
                              (list 'int_selectmode
                                    (mapcar 'mix_strasc
                                            (list(list "{\\C" str_gcol_y ";" 36984 25246 "}")
                                                 (list "{\\C" str_gcol_c ";" 35299 38500 "}")))
                                    ))))
                    (cons "HELP"(lambda()str_guide_selectmode))
                    )
               
               
               (list(list nil)
                    (cons "ITEM"(list ))
                    (list "PAGE" 1)
                    (cons "BOOL"
                          (lambda()
                            T
                            ))
                    (cons
                     "STATUS"
                     (lambda( / bool_depth ii ls_out)
                       
                       (list(list
                             (mix_strasc;;選択中の横断
                              (list 36984 25246 20013 12398 27178 26029 
                                    (if ls_current
                                        (list "  {\\C" str_gcol_y ";" str_currentnumber "}")
                                      (list " {\\C" str_gcol_c ";" 12394 12375 "}"))
                                    )
                              ))))
                     )
                    )
               
               
               (list(list "ENTER");;メインメニューへ
                    (cons "ITEM"(list 12513 12452 12531 12513 12491 12517 12540 12408))
                    (cons "NEXTMODE" "home")
                    )
               
               
               )

              bool_replacegrread T int_grread 2 elem_grread 65
              )
             
             ))
       
       (if(cadr bool) (list ) )
       ))
    
    
    (cons
     "MOVE"
     (lambda( / p);;(d- gr5_home()(progn))

       (cond
        
        ((or ls_drawprofile)
         (setq xx(car elem_grread)yy(cadr elem_grread)
               ls_p(list(list xx yy 0.)(list xx(- yy height_area)0.)
                        (list(+ xx width_area)(- yy height_area)0.)
                        (list(+ xx width_area)yy 0.)
                        (list xx yy 0.)
                        )
               )
         (mapcar '(lambda(p0 p1)(grdraw p0 p1 2))ls_p(cdr ls_p))

         )
        
        (vnam_plane_road

         (setq p_ground
               (car(project_to_ground
                    (list(carxyz elem_grread 0.))vec_view (list nil elev_road)
                    ))
               p_close(vlax-curve-getclosestpointto vnam_plane_road p_ground nil)
               )

         (if bool_snap
             ((lambda( / p d pd)
                (setq p(osnap p_close(strcat str_osnaps str_addsnap)))
                (if(vl-catch-all-error-p
                    (setq d(vl-catch-all-apply 'vlax-curve-getdistatpoint(list vnam_plane_road p))))
                    T
                  (if(if d(setq pd(vlax-curve-getpointatdist vnam_plane_road d)))
                      (if(<(distance p pd)1e-8)(setq p_close p))))
                )))
         
         (grdraw p_ground p_close 2)
         ((lambda(p_close / p vec vec1 vec2 x y ang ang1 ang2)
            (if(setq vec_road(xvla-normal vnam_plane_road p_close))
                (progn
                  (setq vec(trans-x vec_road(list 0 0 1)vec_view)
                        ang(atan(cadr vec)(car vec))
                        ang(+ ang(* 0.9 pi))
                        vec1(list(cos ang)(sin ang)0.)
                        vec1(trans-x vec1 vec_view(list 0 0 1))
                        ang(+ ang(* 0.2 pi))
                        vec2(list(cos ang)(sin ang)0.)
                        vec2(trans-x vec2 vec_view(list 0 0 1))
                        )
                  (mapcar
                   '(lambda(v)
                      (grdraw p_close(mapcar '(lambda(a b)(+ a(* height_text 3. b)))p_close v) 3))
                   (list vec1 vec2))
                  ))
            )
          p_close)

         
         ((lambda(p c / s ls_p)
            (setq s(* height_text 0.8)
                  ls_p(mapcar
                       '(lambda(xx yy)
                          (mapcar '(lambda(a x y)(+ a(* xx x)(* yy y)))
                                  p vec_x_onview vec_y_onview)
                          )
                       (list s(- s)(- s)s) (list s(- s)s(- s)))
                  )
            (mapcar '(lambda(p0 p1)(grdraw p0 p1 c))
                    (list(car ls_p)(caddr ls_p))
                    (list(cadr ls_p)(cadddr ls_p)))
            )
          p_close 3)
         
         
         )
        
        )
       
       ))

    
    
    (cons
     "CLICK"
     (lambda( / p0 p1)
       
       (cond
        
        (ls_drawprofile
         
         (setq x_base(car elem_grread)y_base(cadr elem_grread))
         (mapcar
          '(lambda(lst / str_name height_y str_height ls_ground ls_cross_duct ls_project_duct
                       bool_trans )
             
             (setq str_name(nth 0 lst)
                   base_height(nth 3 lst)
                   height_y(nth 4 lst)
                   str_height(nth 5 lst)
                   ls_ground(nth 6 lst)
                   lst(nth 7 lst)
                   )
             (if(=(car lst)0)(setq ls_cross_duct(cadr lst) bool_trans T)
               (setq ls_project_duct(cadr lst) ))
             
             (setq vnam_text(vla-addtext
                             (vla-get-modelspace
                              (vla-get-activedocument(vlax-get-acad-object)))
                             str_name(vlax-3d-point x_base y_base 0.)
                             0.5)
                   
                   y_base(+ y_base(- height_y))
                   
                   vnam_text(vla-addtext
                             (vla-get-modelspace
                              (vla-get-activedocument(vlax-get-acad-object)))
                             (strcat "DL= " str_height)(vlax-3d-point x_base y_base 0.)
                             0.5)
                   vnam_underbar(vla-addline
                                 (vla-get-modelspace(vla-get-activedocument(vlax-get-acad-object)))
                                 (vlax-3d-point x_base y_base 0.)
                                 (vlax-3d-point(+ x_base 10.)y_base 0.))
                   )

             (setq ls_p(list(list x_base(+ y_base 2.) 0.)(list(+ x_base 1.)(+ y_base 2.)0.)
                            (list x_base (+ y_base 2. ratio_drawverti) 0.)(list x_base(+ y_base 2.) 0.))
                   )

             (mapcar
              '(lambda(p0 p1)
                 (vla-addline
                  (vla-get-modelspace(vla-get-activedocument(vlax-get-acad-object)))
                  (vlax-3d-point p0) (vlax-3d-point p1)) )
              ls_p(cdr ls_p))
             (vla-addtext
              (vla-get-modelspace
               (vla-get-activedocument(vlax-get-acad-object)))
              (strcat "1:"(rtos ratio_drawverti 2 1))(vlax-3d-point(cadr ls_p))
              0.5)
             
             
             
             (if bool_trans
                 (setq vnam(vla-addline
                            (vla-get-modelspace(vla-get-activedocument(vlax-get-acad-object)))
                            (vlax-3d-point(+ x_base(* 0.5 width_area))y_base 0.)
                            (vlax-3d-point(+ x_base(* 0.5 width_area))(+ y_base height_y) 0.))
                       ls_ground(mapcar '(lambda(lst)
                                           (mapcar '+ lst(list(+ x_base(* 0.5 width_area))
                                                              (- y_base base_height)))
                                           )
                                        ls_ground)
                       )
               (setq ls_ground(mapcar '(lambda(lst)(mapcar '+ lst(list x_base(- y_base base_height))) )
                                      ls_ground)
                     )
               )
             
             (setq p0(car ls_ground)p1(cadr ls_ground)ls_ground(cddr ls_ground)
                   ls_p(list p1 p0)
                   ang0(angle p0 p1)
                   )
             
             (while ls_ground
               (setq p0(car ls_ground)ls_ground(cdr ls_ground))
               (if(<(abs(-(setq ang1(angle(car ls_p)p0))ang0))1e-8)
                   (if ls_ground T(setq ls_p(cons p0 ls_p)))
                 (setq ang0 ang1 ls_p(cons p0 ls_p)))
               )
             (setq vnam_ground(xvla-lwpoly(apply 'append(reverse ls_p))(list nil nil :vlax-false))
                   )
             
             
             (mapcar
              '(lambda(lst / xx yy vec_ell ratio_ell ls_para str_layer int_col
                           int_corner ww hh ff rr vnam_duct vnam_protect ls_protect
                           str_name )

                 (mapcar 'set '(xx yy vec_ell ratio_ell ls_para)lst)
                 (setq xx(+ xx x_base(* 0.5 width_area))
                       yy(+ yy y_base(- base_height))
                       str_layer(cdr(assoc "LAYER" ls_para))
                       int_col(cdr(assoc "COLOR" ls_para))
                       int_corner(cdr(assoc "CORNER" ls_para))
                       rr(* 0.5(cdr(assoc "DIAM" ls_para)))
                       str_name(cdr(assoc "INSERTNAME" ls_para))
                       )
                 
                 (if int_corner
                     (setq ww(* 0.5(cdr(assoc "WIDTH" ls_para)))
                           hh(* 0.5(cdr(assoc "HEIGHT" ls_para)))
                           ff(cdr(assoc "FILET" ls_para))))
                 
                 (setq ls_protect
                       (cond
                        ((null int_corner)nil)
                        ((= int_corner 8)
                         (list(list(- ww ff)(- hh))(list ww(- ff hh))
                              (list ww(- hh ff))(list(- ww ff)hh)
                              (list(- ff ww)hh)(list(- ww)(- hh ff))
                              (list(- ww)(- ff hh))(list(- ff ww)(- hh))
                              )
                         )
                        ((= int_corner 4)
                         (list(list ww(- hh))(list ww hh)
                              (list(- ww)hh)(list(- ww)(- hh))
                              )
                         )
                        ((= int_corner -6)
                         (list(list(- ww ff)(- hh))(list ww(- ff hh))
                              (list ww 0.)(list(- ww)0.)
                              (list(- ww)(- ff hh))(list(- ff ww)(- hh))
                              )
                         )
                        ((= int_corner -4)
                         (list(list ww(- hh))(list ww 0.)
                              (list(- ww)0.)(list(- ww)(- hh))
                              )
                         )
                        )
                       )
                 
                 (if(= type_drawcircle "1")
                     (setq vnam_duct
                           (vla-addcircle
                            (vla-get-modelspace(vla-get-activedocument(vlax-get-acad-object)))
                            (vlax-3d-point xx yy 0.)rr)
                           vnam_protect
                           (if ls_protect
                               (xvla-lwpoly
                                ((lambda( / ls_p)
                                   (setq ls_p
                                         (mapcar '(lambda(p)
                                                    (mapcar '+(list xx yy)p))
                                                 ls_protect)
                                         )
                                   (apply 'append ls_p)
                                   ))
                                (list nil nil :vlax-true)
                                )
                             )
                           )
                   
                   (setq vnam_duct
                         (vla-addellipse
                          (vla-get-modelspace(vla-get-activedocument(vlax-get-acad-object)))
                          (vlax-3d-point xx yy 0.) (vlax-3d-point vec_ell)
                          ratio_ell)
                         ;; vnam_protect
                         ;; (if ls_protect
                         ;;     (xvla-lwpoly
                         ;;      ((lambda( / ls_p)
                         ;;         (setq ls_p
                         ;;               (mapcar '(lambda(p)
                         ;;                          (mapcar '+(list xx yy)p))
                         ;;                       ls_protect)
                         ;;               )
                         ;;         (apply 'append ls_p)
                         ;;         ))
                         ;;      (list nil nil :vlax-false)
                         ;;      )
                         ;;   )
                         )
                   )

                 (setq vnam_text(vla-addtext
                                 (vla-get-modelspace
                                  (vla-get-activedocument(vlax-get-acad-object)))
                                 str_name(vlax-3d-point xx yy 0.)
                                 0.25)
                       )
                 
                 (vla-put-layer vnam_duct str_layer)
                 (vla-put-color vnam_duct int_col)
                 vnam_duct
                 )
              
              ls_cross_duct)


             (mapcar
              '(lambda(lst / ls_p ls_para)
                 (setq ls_center(car lst))
                 (if(<(length ls_center)2)T
                   (progn
                     (setq ls_para(cadr lst)
                           str_layer(cdr(assoc "LAYER" ls_para))
                           int_col(cdr(assoc "COLOR" ls_para))
                           int_corner(cdr(assoc "CORNER" ls_para))
                           rr(* 0.5(cdr(assoc "DIAM" ls_para)))
                           str_name(cdr(assoc "INSERTNAME" ls_para))
                           )

                     (if int_corner
                         (setq ww(* 0.5(cdr(assoc "WIDTH" ls_para)))
                               hh(* 0.5(cdr(assoc "HEIGHT" ls_para)))
                               ff(cdr(assoc "FILET" ls_para))))
                     
                     (setq ls_center(mapcar '(lambda(p)(mapcar '+(list x_base 0.)p))ls_center)
                           vnam_duct_center(xvla-lwpoly(apply 'append ls_center)(list nil nil :vlax-false))
                           vnam_offset nil
                           )

                     (setq ls_offset
                           (mapcar
                            '(lambda(ii / ls_p bool_xy)
                               (if(= ii 0)(setq ls_p ls_center)
                                 (if(vl-catch-all-error-p
                                     (setq vnam(vl-catch-all-apply
                                                'vla-offset(list vnam_duct_center(* ii rr)))))
                                     nil
                                   (progn
                                     (setq vnam_offset(car(vlax-safearray->list(vlax-variant-value vnam)))
                                           ls_p(vlax-safearray->list(vlax-variant-value(vla-get-coordinates vnam_offset)))
                                           ls_p(split_list 2 ls_p)
                                           )
                                     )))
                               
                               (if(and(= ii 1)ls_p)(vla-delete vnam_offset))
                               (mapcar '(lambda(p)
                                          (list(car p)
                                               (+(*(cadr p)ratio_drawverti)y_base(- base_height)))
                                          )
                                       ls_p)
                               )
                            (list 1 -1 0))
                           )
                     
                     (if vnam_offset
                         (progn
                           (setq ls_p(apply 'append(append(car ls_offset)(reverse(cadr ls_offset)))))
                           (setq array_p(vlax-make-safearray vlax-vbDouble(cons 0 (1-(length ls_p)))))
                           (vlax-safearray-fill array_p ls_p)
                           (vla-put-coordinates vnam_offset array_p)
                           (vla-put-closed vnam_offset :vlax-true)
                           (vla-put-layer vnam_offset str_layer)
                           (vla-put-color vnam_offset int_col)
                           ))
                     
                     (setq ls_p(apply 'append(caddr ls_offset)))
                     (setq array_p(vlax-make-safearray vlax-vbDouble(cons 0 (1-(length ls_p)))))
                     (vlax-safearray-fill array_p ls_p)
                     (vla-put-coordinates vnam_duct_center array_p)

                     (setq vnam_number
                           (vla-addtext
                            (vla-get-modelspace(vla-get-activedocument(vlax-get-acad-object)))
                            str_name(vlax-3d-point(car ls_p)(cadr ls_p)0.)
                            0.25)
                           )

                     ))
                 )
              ls_project_duct)
             
             (setq y_base(+ y_base(* -1. space_drawing)))
             
             )
          ls_drawprofile)
         
         (setq ls_drawprofile nil)
         )
        ((and bool_select_plane_road ls_vnam_select)
         
         (if(setq vnam_plane_road
                  ((lambda( / vnam )
                     (setq vnam(car ls_vnam_select))
                     (if(or(vl-catch-all-error-p
                            (setq p0(vl-catch-all-apply 'vlax-curve-getstartpoint(list vnam))))
                           (vl-catch-all-error-p
                            (setq p1(vl-catch-all-apply 'vlax-curve-getendpoint(list vnam)))))
                         nil
                       vnam))))
             (progn
               (setq elev_road(* 0.5(+(caddr p0)(caddr p1)))
                     bool_point T
                     bool_selectent nil bool_select nil int_selectmode -1
                     ls_ssget nil ls_ssgetinsert nil
                     bool_select_plane_road nil
                     int_commandpage 1
                     )
               (exckillobj vnam_plane_road)
               ))
         
         (vla-getXData vnam_plane_road "terraduct3d" 'array_Type 'array_Data )
         (setq ls_xdata
               (if array_data
                   (split_list 0(mapcar 'vlax-variant-value
                                        (vlax-safearray->list array_data))))
               )


         (if(=(cdar ls_xdata)"PLANEROAD")
             (progn
               (setq ls_xdata(cdr ls_xdata))
               (if(setq lst(assoc "REVERSE" ls_xdata))
                   (setq int_transdirection(cdr lst)
                         ls_xdata(vl-remove lst ls_xdata)))
               (setq ls_xroadnumber
                     (split_list 3(mapcar 'cdr ls_xdata))
                     )
               
               ) )
         
         (setq ls_vnam_number(list))
         (setq ls_vnam_number
               (mapcar
                '(lambda(lst / dd str pp ww ii str_ii ang )
                   (setq str(car lst)dd(cadr lst)ww(caddr lst))
                   (func_road_number
                    (list(cons "NUMBER" str)
                         (cons "DIST" dd)(cons "WIDTH" ww)))
                   )
                ls_xroadnumber)
               )
         
         (setq ls_vnam_number(reverse ls_vnam_number))
         (if(setq ls_current(car ls_vnam_number))
             (setq str_currentnumber(cdr(assoc "NUMBER" ls_current))))
         
         (mapcar '(lambda(v)(vla-Highlight v :vlax-false))ls_vnam_select)
         (setq ls_vnam_select nil ls_vnam_highlight nil)
         

         )
        
        (vnam_plane_road
         
         (if((lambda( / vnam ls_out)
               (if(setq set_ent(ssget p_close(list(list -3(list "terraduct3d")))))
                   (progn
                     (setq entna(ssname set_ent 0) vnam(vlax-ename->vla-object entna))
                     (vla-getXData vnam "terraduct3d" 'array_Type 'array_Data )
                     (setq ls_xdata
                           (if array_data
                               (split_list 0(mapcar 'vlax-variant-value
                                                    (vlax-safearray->list array_data))))
                           str_type(cdr(assoc "terraduct3d" ls_xdata)))

                     (if(= str_type "ROADNUMBERTEMP")
                         (setq vnam(vlax-ename->vla-object
                                    (handent(cdr(assoc "LINE" ls_xdata))))
                               ls_out(assoc(cons "LINE" vnam)ls_vnam_number)
                               ))
                     (if ls_out(setq ls_current ls_out
                                     str_currentnumber(cdr(assoc "NUMBER" ls_current)) ))
                     ))
               ))
             T

           (progn
             (setq ls_vnam_number
                   (cons(func_road_number
                         (list(cons "POINT" p_close)(cons "WIDTH" width_road_profile)))
                        ls_vnam_number)
                   ls_current(car ls_vnam_number)
                   str_currentnumber(cdr(assoc "NUMBER" ls_current))
                   )
             (save_road_number)
             )
           )
         
         )
        
        )
       
       )
     )

    (cons
     "KEYBOAD"
     (lambda( / ls_str_out num ls_out_parameter str_out)
       (cond
        (bool_select_plane_road
         (setq bool_select_plane_road nil
               int_selectmenu nil
               int_commandpage 0
               )
         )
        )
       ))
    
    
    )

   (list
    "senkeidraw" ;;edsym
    (cons
     "INITIAL"
     (lambda(bool);;initial
       (if(car bool)
           (progn
             ;;temp
             (setq bool_point nil
                   bool_selectent nil bool_select nil int_selectmode 0
                   ls_vnam_select nil
                   )

             (setq p_cloth1 nil int_colcloth1 20
                   p_cloth2 nil int_colcloth2 40
                   p_cloth3 nil int_colcloth3 60
                   p_cloth4 nil int_colcloth4 80
                   a1_cloth 100. rr_cloth 1000. a2_cloth 100.
                   delta_cloth 1.
                   )
             
             
             (setq
              func_guidemenu
              (lambda()
                (mix_strasc
                 (list (if ls_vnam_select(list 26377 12426)(list 28961 12375)) 12305
                       )
                 ) )
              
              ls_guideexplane
              (mapcar
               ;;点1,点2と点3,点4の交点がIP点になります
               ;;点4を選ばないとき、点2がIP点になります
               'mix_strasc
               (list
                (list 28857 "1," 28857 "2" 12392 28857 "3," 28857 "4" 12398 20132 28857 12364 "IP" 28857 12395 12394 12426 12414 12377 )
                (list 28857 "4" 12434 36984 12400 12394 12356 12392 12365 12289 28857 "2" 12364 "IP" 28857 12395 12394 12426 12414 12377 )
                ))
              
              
              ls_guidemenu
              (list
               
               (list(list 49);;点1
                    (cons "ITEM"(list 28857 "1" ))
                    (cons "GETPOINT" (lambda() (list p_cloth1(itoa int_colcloth1))))
                    (cons "LOADFUNCTION"
                          (lambda(bool)
                            (setq int_selectmenu nil)
                            (if bool(setq p_cloth1 elem_grread))
                            (setq bool_replacegrread T int_grread 2 elem_grread 50)
                            )
                          )
                    )
               (list(list 50);;点2
                    (cons "ITEM"(list 28857 "2" ))
                    (cons "GETPOINT" (lambda() (list p_cloth2(itoa int_colcloth2))))
                    (cons "LOADFUNCTION"
                          (lambda(bool)
                            (setq int_selectmenu nil)
                            (if bool(setq p_cloth2 elem_grread))
                            (setq bool_replacegrread T int_grread 2 elem_grread 51)
                            )
                          )
                    )
               (list(list 51);;点3
                    (cons "ITEM"(list 28857 "3" ))
                    (cons "GETPOINT" (lambda() (list p_cloth3(itoa int_colcloth3))))
                    (cons "LOADFUNCTION"
                          (lambda(bool)
                            (setq int_selectmenu nil)
                            (if bool(setq p_cloth3 elem_grread))
                            (setq bool_replacegrread T int_grread 2 elem_grread 52)
                            )
                          )
                    )
               (list(list 52);;点4
                    (cons "ITEM"(list 28857 "4" ))
                    (cons "GETPOINT" (lambda() (list p_cloth4(itoa int_colcloth4))))
                    (cons "LOADFUNCTION"
                          (lambda(bool)
                            (setq int_selectmenu nil)
                            (if bool(setq p_cloth4 elem_grread))
                            )
                          )
                    )
               
               (list(list 82)
                    (cons "ITEM"(list "R"))
                    (cons "INPUT"(lambda() 'rr_cloth))
                    )
               (list(list 65)
                    (cons "ITEM"(list "A1"))
                    (cons "INPUT"(lambda() 'a1_cloth))
                    )
               (list(list 90)
                    (cons "ITEM"(list "A2"))
                    (cons "INPUT"(lambda() 'a2_cloth))
                    )
               (list(list 68)
                    (cons "ITEM"(list 12463 12525 12477 12452 12489 12500 12483 12481 ))
                    (cons "INPUT"(lambda() 'delta_cloth))
                    )
               
               (list(list 67);;断面作成に戻る
                    (cons "ITEM"(list 26029 38754 20316 25104 12395 25147 12427 ))
                    (cons "NEXTMODE" "profiledrawing");;
                    )
               
               )
              
              
              )
             
             ))
       
       (if(cadr bool) (list ) )
       ))

    (cons
     "MOVE"
     (lambda();;gr5
       (mapcar
        '(lambda(p c / s ls_p)
           (if p
               (progn
                 (setq s(* height_text 0.8)
                       ls_p(mapcar
                            '(lambda(xx yy)
                               (mapcar '(lambda(a x y)(+ a(* xx x)(* yy y)))
                                       p vec_x_onview vec_y_onview)
                               )
                            (list s(- s)(- s)s) (list s(- s)s(- s)))
                       )
                 (mapcar '(lambda(p0 p1)(grdraw p0 p1 c))
                         (list(car ls_p)(caddr ls_p))
                         (list(cadr ls_p)(cadddr ls_p)))
                 ))
           )
        (list p_cloth1 p_cloth2 p_cloth3 p_cloth4 )
        (list int_colcloth1 int_colcloth2 int_colcloth3 int_colcloth4)
        )
       ))
    
    (cons
     "KEYBOAD"
     (lambda( / ls_str_out num ls_out_parameter str_out)

       (if(and(or(= elem_grread 13)(= int_grread 25))p_cloth1 p_cloth2 p_cloth3 )
           (progn
             (setq p_cloth1(carxy p_cloth1) p_cloth2(carxy p_cloth2) p_cloth3(carxy p_cloth3))
             (if p_cloth4
                 (setq p_cloth4(carxy p_cloth4)
                       p_cloth2(inters p_cloth1 p_cloth2 p_cloth3 p_cloth4 nil)
                       p_cloth3 p_cloth4))
             
             (setq vnam(cloth_road_point
                        p_cloth1 p_cloth2 p_cloth3
                        (float rr_cloth)(float a1_cloth)(float a2_cloth)(float delta_cloth))
                   )
             
             
             (setq p_cloth1 nil p_cloth2 nil p_cloth3 nil p_cloth4 nil)
             ))
       
       ))
    
    ;;CLICK,KEYBOAD
    
    )
   
   
   
   )
  )



(defun geo3d()

  (search_sty-lay-blo
   (list(cons "STYLE" 'ls_textstyle)
        (cons "DIMSTYLE" 'ls_dimstyle)
        (cons "LAYER" 'ls_layername)
        ))

  (setq pitch_mesh 0.5)
  (setq set_ent(ssget "X")
        num(if set_ent(sslength set_ent)0)
        ls_dwduct(list)ls_obj(list))
  
  (while(>(setq num(1- num))-1)
    (setq vnam (vlax-ename->vla-object(ssname set_ent num))
          vnam_links (vla-get-Hyperlinks vnam))

    (setq num_link (vla-get-Count vnam_links))
    (while(>(setq num_link(1- num_link))-1)
      (setq vnam_link(vla-Item vnam_links num_link))
      (setq ls_obj(cons(list(vla-get-URLDescription vnam_link)vnam
                            (vla-get-URL vnam_link)
                            (vla-get-URLNamedLocation vnam_link)
                            )
                       ls_obj )
            )
      )
    )

  (while ls_obj
    (setq lst(car ls_obj)ls_obj(cdr ls_obj)
          str(car lst)vnam(cadr lst)
          ls_vnam(list vnam)
          )
    (while(setq lst(assoc str ls_obj))
      (setq ls_vnam(cons(cadr lst)ls_vnam)
            ls_obj(vl-remove lst ls_obj))
      )
    (if(<(length ls_vnam)2)
        T ;;1本しかない
      (progn
        (if(=(length ls_vnam)2)T
          (progn
            
            (setq ls_pcoord
                  (mapcar
                   '(lambda(vnam / ls_p)
                      (if(vl-catch-all-error-p
                          (setq ls_p(vl-catch-all-apply 'vla-get-coordinates(list vnam))))
                          (setq ls_p(mapcar '(lambda(func)(func vnam))
                                            (list vlax-curve-getstartpoint vlax-curve-getendpoint)))
                        (setq ls_p(vlax-safearray->list(vlax-variant-value ls_p))
                              ls_p(split_list
                                   (if(=(vla-get-ObjectName vnam)"AcDb3dPolyline")3
                                     (if(=(vla-get-ObjectName vnam)"AcDbPolyline")2))
                                   ls_p)
                              )
                        )
                      (cons vnam ls_p))
                   ls_vnam)
                  
                  ls_vnam(list)
                  )
            
            ((lambda( / bool_loop ls_dummy)
               (while ls_pcoord
                 (if ls_dummy T
                   (setq ls_p(car ls_pcoord) vnam(car ls_p)ls_p(cdr ls_p)
                         ls_dummy ls_pcoord
                         ))
                 (setq bool_delete nil)
                 (while(setq ls_dummy(cdr ls_dummy))
                   (setq lst(car ls_dummy)ls_px(cdr lst)vnamx(car lst)
                         bool_union nil)

                   (cond
                    ((<(distance(car ls_p)(car ls_px))1e-8)
                     (setq ls_p(append(reverse ls_px)(cdr ls_p))
                           bool_delete T bool_union T)
                     )
                    ((<(distance(car ls_p)(last ls_px))1e-8)
                     (setq ls_p(append ls_px(cdr ls_p))
                           bool_delete T bool_union T)
                     )
                    ((<(distance(last ls_p)(car ls_px))1e-8)
                     (setq ls_p(append ls_p(cdr ls_px))
                           bool_delete T bool_union T)
                     )
                    ((<(distance(last ls_p)(last ls_px))1e-8)
                     (setq ls_p(append ls_p(cdr(reverse ls_px)))
                           bool_delete T bool_union T)
                     )
                    )
                   (if bool_union
                       (progn
                         (setq ls_pcoord(vl-remove lst ls_pcoord))
                         (vla-delete vnamx)
                         ))
                   (if(and bool_delete(null ls_dummy))(setq ls_dummy ls_pcoord))
                   )
                 
                 (setq ls_vnam(cons(cons vnam ls_p)ls_vnam)
                       ls_pcoord(cdr ls_pcoord))
                 )
               ))
            

            (setq ls_vnam
                  (mapcar
                   '(lambda(lst / vnam)
                      (setq vnam(car lst)lst(cdr lst) )
                      (setq ls_p(apply 'append lst) )
                      (setq array_p(vlax-make-safearray vlax-vbDouble(cons 0 (1-(length ls_p)))))
                      (vlax-safearray-fill array_p ls_p)
                      (vla-put-coordinates vnam array_p)
                      vnam)
                   ls_vnam)
                  )
            
            ))
        
        
        (setq ls_dwduct(cons(cons str ls_vnam)ls_dwduct))
        ))
    
    )
  
  
  (if str_path_tempdirectory T
    (progn
      (setq path_dcl(if command_for_alter(vl-filename-mktemp ".dcl")
                      (vl-filename-mktemp "0" "0" ".dcl") )
            nn(strlen path_dcl) )
      (while(/=(substr path_dcl nn 1)"\\")(setq nn(1- nn)))
      (setq str_path_tempdirectory(substr path_dcl 1 nn) )
      ))
  
  (progn ;;ground
    (setq path_geo2dto3d(strcat str_path_tempdirectory "geo2dto3d.dcl") 
          open_file (open path_geo2dto3d "w")
          )

    (setq ls_geolayer
          (list(list(mix_strasc(list 32294 26029 22259 12479 12452 12488 12523 12392 20596 38754 22259 20301 32622  ))
                    "drawtitle"(mix_strasc(list "00GEO" 12399 12383 12354 12370 ))'str_lay_title)
               ;;側面図タイトルと側面図位置,00GEOはたあげ
               (list(mix_strasc(list 32294 26029 22259 12464 12522 12483 12489 ))
                    "drawgrid"(mix_strasc(list "GCube_SCALE_GRID")) 'str_lay_grid)
               ;;側面図グリッド,
               (list(mix_strasc(list 32294 26029 22259 36600 20516 ))
                    "drawscale"(mix_strasc(list "GCube_SCALE_LABEL")) 'str_lay_scale)
               ;;縦断図軸値
               )
          )

    (setq ls_ductnum(inclist 0(length ls_dwduct)))
    (write_strlist
     open_file
     (list
      "Sedit :dialog"
      "{"
      (mix_strasc;;使用するオブジェクトの画層設定
       (list " label = \"" 20351 29992 12377 12427 12458 12502 12472 12455 12463 12488 12398 30011 23652 35373 23450 "\";"))

      (mapcar
       '(lambda(lst / str str_key )
          (setq str(car lst)str_key(cadr lst))
          (list
           " :row"
           " {"
           "  alignment = left;"
           "  fixed_width = true;"
           (list_to_dcltext
            (list "text"(cons "width" "30")(cons "fixed_width" "true")(cons "value" str)))
           (list_to_dcltext
            (list "popup_list"(cons "width" "30")(cons "fixed_width" "true")(cons "key" str_key)))
           "  }"
           )
          )
       ls_geolayer
       )


      " spacer;"
      
      " :row"
      " {"
      "  alignment = left;"
      "  fixed_width = true;"
      (list_to_dcltext;;平面図の単位
       (list "text"(cons "width" "30")(cons "fixed_width" "true")
             (cons "value" (mix_strasc(list  24179 38754 22259 12398 21336 20301  )))))
      (list_to_dcltext
       (list "popup_list"(cons "width" "30")(cons "fixed_width" "true")
             (cons "key" "unitplane")))
      "  }"
      " :row"
      " {"
      "  alignment = left;"
      "  fixed_width = true;"
      (list_to_dcltext;;縦断図に記載された文字の単位
       (list "text"(cons "width" "30")(cons "fixed_width" "true")
             (cons "value" (mix_strasc(list 32294 26029 22259 12395 35352 36617 12373 12428 12383 25991 23383 12398 21336 20301 )))))
      (list_to_dcltext
       (list "popup_list"(cons "width" "30")(cons "fixed_width" "true")
             (cons "key" "unitside")))
      "  }"

      " spacer;"
      " :row"
      " {"
      "  alignment = left;"
      "  fixed_width = true;"
      (list_to_dcltext;;管オブジェクト作成方法
       (list "text"(cons "width" "30")(cons "fixed_width" "true")
             (cons "value" (mix_strasc(list 31649 12458 12502 12472 12455 12463 12488 20316 25104 26041 27861  )))))
      (list_to_dcltext
       (list "popup_list"(cons "width" "30")(cons "fixed_width" "true")
             (cons "key" "ductsolid")))
      "  }"

      
      
      
      (list_to_dcltext;;モデルはm単位で作成されます
       (list "text"(cons "width" "60")(cons "fixed_width" "true")
             (cons "value"(mix_strasc(list 12514 12487 12523 12399 "m" 21336 20301 12391 20316 25104 12373 12428 12414 12377 )))))
      (list_to_dcltext;;平面図単位に「mm」を選んだとき、平面図位置には作成できないので
       (list "text"(cons "width" "60")(cons "fixed_width" "true")
             (cons "value"(mix_strasc(list 24179 38754 22259 21336 20301 12395 12300 "mm" 12301 12434 36984 12435 12384 12392 12365 12289
                                           24179 38754 22259 20301 32622 12395 12399 20316 25104 12391 12365 12394 12356 12398 12391 )))))
      (list_to_dcltext;;モデル生成位置を指定する必要があります
       (list "text"(cons "width" "60")(cons "fixed_width" "true")
             (cons "value"(mix_strasc(list 12514 12487 12523 29983 25104 20301 32622 12434 25351 23450 12377 12427 24517 35201 12364 12354 12426 12414 12377 )))))
      
      

      " spacer;"
      
      " :boxed_column"
      " {";;
      (mix_strasc(list "  label = \"" 12458 12502 12472 12455 12463 12488 12372 12392 12398 12497 12521 12513 12540 12479  20837 21147 "\";"))

      (list_to_dcltext;;※ハイパーリンクが設定されていることを想定しています
       (list "text"(cons "width" "60")(cons "fixed_width" "true")
             (cons "value"(mix_strasc(list 12495 12452 12497 12540 12522 12531 12463 12364 35373 23450 12373 12428 12390 12356 12427 12371 12392 12434 24819 23450 12375 12390 12356 12414 12377 )))))

      (list_to_dcltext;;正の値のとき、その直径の管を生成
       (list "text"(cons "width" "60")(cons "fixed_width" "true")
             (cons "value"(mix_strasc(list 27491 12398 20516 12398 12392 12365 12289 12381 12398 30452 24452 12398 31649 12434 29983 25104 )))))
      (list_to_dcltext;;負の値のとき、その絶対値の厚みの板状オブジェクトを生成
       (list "text"(cons "width" "60")(cons "fixed_width" "true")
             (cons "value"(mix_strasc(list 36000 12398 20516 12398 12392 12365 12289 12381 12398 32118 23550 20516 12398 21402 12415 12398 26495 29366 12458 12502 12472 12455 12463 12488 12434 29983 25104 )))))
      " :row"
      " {"
      "  alignment = left;"
      "  fixed_width = true;"
      (list_to_dcltext;;すべて出力
       (list "button"(cons "width" "16")(cons "fixed_width" "true")
             (cons "label"(mix_strasc(list 12377 12409 12390 20986 21147 )))(cons "key" "allselecton")))
      (list_to_dcltext;;すべて解除
       (list "button"(cons "width" "16")(cons "fixed_width" "true")
             (cons "label"(mix_strasc(list 12377 12409 12390 35299 38500 )))(cons "key" "allselectoff")))

      "  }"
      
      " :row"
      " {"
      (mapcar
       '(lambda(lst ii / str  )
          (list
           " :column"
           " {"
           "  alignment = top;"
           "  fixed_height = true;"

           
           (mapcar
            '(lambda(lst ii / str)
               (if(setq str(car lst))
                   (list
                    " :row"
                    " {"
                    "  alignment = left;"
                    "  fixed_width = true;"
                    (list_to_dcltext
                     (list "toggle"(cons "width" "5")(cons "fixed_width" "true")
                           (cons "key"(strcat "toggle"(itoa ii)))))
                    (list_to_dcltext
                     (list "text"(cons "width" "10")(cons "fixed_width" "true")
                           (cons "value" str)
                           ))
                    (list_to_dcltext
                     (list "edit_box"(cons "width" "10")(cons "fixed_width" "true")
                           (cons "value" "0.2")
                           (cons "key"(strcat "duct"(itoa ii)))))
                    (list_to_dcltext
                     (list "text"(cons "width" "5")(cons "fixed_width" "true") ))
                    "  }"
                    )
                 (list
                  " :row"
                  " {"
                  (list_to_dcltext
                   (list "text"(cons "width" "10")(cons "fixed_width" "true")))
                  "  }"
                  )
                 )
               )
            lst ii)

           
           
           "  }"
           )
          )
       (split_list 10 ls_dwduct)
       (split_list 10 ls_ductnum)
       )
      "   }"
      "  }"

      
      
      " ok_cancel;"
      " }";//end
      )
     )
    
    (close open_file)

    (setq settile_geo2dto3d
          (lambda( / func_las bool_loop str_inputdata)
            (setq bool_loop T)

            (mapcar
             '(lambda(lst / str_key str_default str_int int_layer)
                (setq str_key(cadr lst)str_default(caddr lst))
                (if(setq int_layer(vl-position str_default ls_layername))T
                  (setq int_layer 0))
                (start_list str_key)
                (mapcar 'add_list ls_layername)
                (end_list)
                (set_tile str_key (itoa int_layer))
                
                )
             ls_geolayer
             )

            (start_list "unitplane")
            (mapcar 'add_list(list "m" "mm"))
            (end_list)
            ;; (set_tile "unitplane" "1")
            (start_list "unitside")
            (mapcar 'add_list(list "m" "mm"))
            (end_list)
            (start_list "ductsolid")
            (mapcar 'add_list(list "MESH" "SOLID"))
            (end_list)

            (action_tile "allselecton" "(button_select T)")
            (action_tile "allselectoff" "(button_select nil)")
            (action_tile "accept" "(accept_geo2dto3d)")
            )
          
          button_select
          (lambda(bool / str_toggle)
            (setq str_toggle(if bool "1" "0"))
            (mapcar
             '(lambda(lst ii / str)
                (set_tile(strcat "toggle"(itoa ii))str_toggle))
             ls_dwduct ls_ductnum)
            )
          
          accept_geo2dto3d
          (lambda( / )
            (mapcar
             '(lambda(lst / str_key sym int_layer str_lay)
                (setq str_key(cadr lst)sym(cadddr lst)
                      int_layer(atoi(get_tile str_key))
                      str_lay(nth int_layer ls_layername)
                      )
                (set sym str_lay)
                )
             ls_geolayer)

            (setq ls_duct_diam(list))
            (mapcar
             '(lambda(lst ii / str)
                (if(=(get_tile(strcat "toggle"(itoa ii)))"1")
                    (setq ls_duct_diam(cons(cons(car lst)(atof(get_tile(strcat "duct"(itoa ii)))))
                                           ls_duct_diam)
                          )))
             ls_dwduct ls_ductnum)
            
            (setq str_ductsolidmesh(get_tile "ductsolid"))

            
            (setq int_unit_plane(atoi(get_tile "unitplane"))
                  int_unit_side(atoi(get_tile "unitside")))
            
            (done_dialog 1)
            )
          
          )
    

    (setq load_dcl (load_dialog path_geo2dto3d))
    (new_dialog "Sedit" load_dcl)
    (settile_geo2dto3d)

    (setq dialog-box (start_dialog))
    (unload_dialog load_dcl)

    
    
    )

  (if(=(getvar "DIASTAT")0)
      (progn(princ "CANCELED"))
    (progn
      

      (setq set_ent(ssget "X"(list(cons 8 str_lay_grid)))
            num(if set_ent(sslength set_ent)0)
            ls_dwgrid(list)ls_obj(list))
      (while(>(setq num(1- num))-1)
        (setq vnam (vlax-ename->vla-object(ssname set_ent num)))
        
        (if(or(vl-catch-all-error-p
               (vl-catch-all-apply 'vlax-curve-getstartpoint(list vnam)))
              (vl-catch-all-error-p
               (vl-catch-all-apply 'vlax-curve-getendpoint(list vnam))))
            T
          (setq ls_obj(cons vnam ls_obj))
          )
        )

      ;;交差するものだけでグループ化する
      (setq func_crossgroup
            (lambda(lst vnam / ls_out)
              (while lst
                (setq ls_out(car lst))
                (if(vl-position vnam ls_out)(setq lst nil)
                  (setq ls_out nil lst(cdr lst)))
                )
              ls_out))
      
      (setq int_draw -1)
      (while ls_obj
        (setq vnam1(car ls_obj)ls_obj(cdr ls_obj)ls_dummy ls_obj
              ls_prev(func_crossgroup ls_dwgrid vnam1)
              ls_current (if ls_prev ls_prev(list vnam1))
              )
        
        (while ls_dummy
          (setq vnam2(car ls_dummy)ls_dummy(cdr ls_dummy))
          (if(get_inters_point_vna vnam1 vnam2 00)
              (if ls_prev
                  (if(vl-position vnam2 ls_current)T
                    (setq ls_current(cons vnam2 ls_current)))
                (if(setq ls_prev(func_crossgroup ls_dwgrid vnam2))
                    (setq ls_current(cons vnam1 ls_prev))
                  (setq ls_prev(list vnam1 vnam2)ls_dwgrid(cons ls_prev ls_dwgrid)
                        ls_current ls_prev)
                  
                  )))
          
          )
        (setq ls_dwgrid(if ls_prev(subst ls_current ls_prev ls_dwgrid)
                         (cons ls_current ls_dwgrid)))
        )

      (setq ls_gridcoordinate
            (mapcar
             '(lambda(lst / ls_out ls_x ls_y x_min x_max y_min y_max)
                (while lst
                  (setq vnam(car lst)lst(cdr lst))
                  (if(vl-catch-all-error-p
                      (setq ls_p(vl-catch-all-apply 'vla-get-coordinates(list vnam))))
                      (setq ls_p(mapcar '(lambda(func)(func vnam))
                                        (list vlax-curve-getstartpoint vlax-curve-getendpoint)))

                    (setq ls_p(vlax-safearray->list(vlax-variant-value ls_p))
                          ls_p(split_list
                               (if(=(vla-get-ObjectName vnam)"AcDb3dPolyline")3
                                 (if(=(vla-get-ObjectName vnam)"AcDbPolyline")2))
                               ls_p)
                          )
                    )

                  (if x_min
                      (setq x_min(apply 'min(cons x_min(mapcar 'car ls_p)))
                            x_max(apply 'max(cons x_max(mapcar 'car ls_p)))
                            y_min(apply 'min(cons y_min(mapcar 'cadr ls_p)))
                            y_max(apply 'max(cons y_max(mapcar 'cadr ls_p)))
                            )
                    (setq x_min(apply 'min(mapcar 'car ls_p))
                          x_max(apply 'max(mapcar 'car ls_p))
                          y_min(apply 'min(mapcar 'cadr ls_p))
                          y_max(apply 'max(mapcar 'cadr ls_p))
                          )
                    )
                  
                  (if(>(length ls_p)2)
                      (setq ls_p nil));;(cons(last ls_p)ls_p)
                  
                  (mapcar
                   '(lambda(p0 p1 / ang)
                      (setq ang(angle p0 p1))
                      ((lambda(i / xy sym val)
                         (if(= i 0) (setq xy(car p0)sym 'ls_x val ls_x)
                           (if(= i 1)(setq xy(cadr p0)sym 'ls_y val ls_y)))
                         (if xy
                             ((lambda( /  )
                                (if(apply 'or(mapcar '(lambda(a) (<(abs(- xy a))1e-8))val))T
                                  (set sym(cons xy val)))))
                           )
                         )
                       (if(<(abs(cos ang))1e-8)0
                         (if(<(abs(sin ang))1e-8)1)))
                      
                      )
                   ls_p(cdr ls_p))
                  )
                (list(list x_min x_max y_min y_max)ls_x ls_y)
                )
             ls_dwgrid)
            ls_rangegrid(mapcar 'car ls_gridcoordinate)
            ls_gridcoordinate(mapcar 'cdr ls_gridcoordinate)
            ls_gridcoordinate
            (mapcar '(lambda(lst) (mapcar '(lambda(a)(vl-sort a '<))lst))
                    ls_gridcoordinate)
            )
      
      (setq ls_p_grid
            (mapcar '(lambda(lst / ls_x ls_y x_min y_min)
                       (setq ls_x(car lst)ls_y(cadr lst)
                             x_min(car ls_x)y_min(car ls_y))
                       (list
                        (mapcar '(lambda(x)(list x y_min))ls_x)
                        (mapcar '(lambda(y)(list x_min y))ls_y)
                        )
                       )
                    ls_gridcoordinate)
            )

      (setq set_ent(ssget "X"(list(cons 8 str_lay_scale)))
            num(if set_ent(sslength set_ent)0)
            ls_dwgrid(list)ls_obj(list)
            textheight_temp nil
            )
      (while(>(setq num(1- num))-1)
        (setq vnam (vlax-ename->vla-object(ssname set_ent num)))
        
        (if(or(vl-catch-all-error-p
               (setq p_a(vl-catch-all-apply 'vla-get-textalignmentpoint(list vnam))))
              (vl-catch-all-error-p
               (setq p_i(vl-catch-all-apply 'vla-get-insertionpoint(list vnam))))
              (vl-catch-all-error-p
               (setq str(vl-catch-all-apply 'vla-get-textstring(list vnam))))
              )
            T
          (progn;;縦断図寸法テキストは下と左にある
            (if textheight_temp T
              (setq textheight_temp(vla-get-height vnam) 
                    ls_p_grid
                    (mapcar '(lambda(lst / ls_x ls_y x_min y_min)
                               (setq ls_x(car lst)ls_y(cadr lst))
                               (list
                                (mapcar '(lambda(p)(mapcar '+ p(list 0.(- textheight_temp)0.)))
                                        ls_x)
                                ls_y
                                )
                               )
                            ls_p_grid)
                    )
              )
            
            (while(progn(setq ii(ascii(substr str 1 1)))
                        (or(= ii 47)(< ii 45)(> ii 57))
                        )
              (setq str(substr str 2))
              )

            (setq val(atof str))
            (setq p_a(vlax-safearray->list(vlax-variant-value p_a)))
            (if(<(distance(list 0 0 0)p_a)1e-8)
                (setq p_a(vlax-safearray->list(vlax-variant-value p_i))))
            (setq dd_min nil num_draw -1)
            
            (mapcar '(lambda(lst / ls_x ls_y x_min y_min)
                       (setq num_draw(1+ num_draw) num_xy -1)
                       (mapcar '(lambda(ls_p)
                                  (setq num_xy(1+ num_xy)num_point -1)
                                  (mapcar '(lambda(p)
                                             (setq num_point(1+ num_point)
                                                   dd(distance p p_a))
                                             (if(if dd_min(< dd dd_min)T)
                                                 (setq dd_min dd ls_int(list num_draw num_xy num_point)))
                                             )
                                          ls_p)
                                  )
                               lst)
                       )
                    ls_p_grid)
            
            (setq ls_obj(cons(list ls_int val)ls_obj))
            )
          )
        )

      (setq num_draw -1
            ls_valgrid
            (mapcar '(lambda(lst / ls_x ls_y x_min y_min)
                       (setq num_draw(1+ num_draw) num_xy -1)
                       (mapcar '(lambda(ls_p)
                                  (setq num_xy(1+ num_xy)num_point -1)
                                  (vl-remove
                                   nil
                                   (mapcar '(lambda(p)
                                              (setq num_point(1+ num_point))
                                              (if(setq val(cadr(assoc(list num_draw num_xy num_point)ls_obj)))
                                                  (list((if(= num_xy 0)car cadr)p)val))
                                              )
                                           ls_p)
                                   )
                                  )
                               lst)
                       )
                    ls_p_grid)
            
            ls_valgrid
            (mapcar
             '(lambda(lst)
                (mapcar '(lambda(ls_p / lst1 lst2 dmin dmax scale_grid)
                           (if(<(length ls_p)2)
                               (progn (alert "nogrid")(quit)))
                           
                           (setq lst1(car ls_p)lst2(last ls_p)
                                 dmin(car lst1)dmax(car lst2)
                                 scale_grid(/(-(cadr lst2)(cadr lst1))(- dmax dmin))
                                 )
                           
                           (if(= int_unit_side 1)(setq scale_grid(* scale_grid 0.001)))
                           (list dmin dmax scale_grid(cadr lst1))
                           )
                        lst))
             ls_valgrid)
            
            )
      
      (setq ls_pgrid_lefttop(mapcar '(lambda(lst)(last(cadr lst)) ) ls_p_grid))
      
      (setq set_ent(ssget "X"(list(cons 8 str_lay_title)))
            num(if set_ent(sslength set_ent)0)
            ls_dwslice(list)ls_obj(list))
      (while(>(setq num(1- num))-1)
        (setq vnam (vlax-ename->vla-object(ssname set_ent num))
              str_obj(vla-get-objectname vnam) )
        (if(vl-catch-all-error-p
            (setq str(vl-catch-all-apply 'vla-get-textstring(list vnam))))
            (setq str(vl-catch-all-apply 'vla-get-TextOverride(list vnam))))
        (setq ls_obj(cons(list str_obj str vnam)ls_obj))
        )

      (while(setq ls_vnam(assoc "AcDbText" ls_obj))
        (setq ls_obj(vl-remove ls_vnam ls_obj)
              str(cadr ls_vnam) vnam_text(caddr ls_vnam))
        (setq str_key(vl-string-trim
                      (mix_strasc(list "()" 65288 65289 "[]" 65339 65341
                                       12304 12305 "{}" 65371 65373 "<>" 65308 65310 ))
                      str)
              
              str_key(strcat "*" str_key "*"))
        
        (setq entna_dim
              ((lambda(lst / ls_out)
                 (while lst
                   (setq ls_out(car lst))
                   (if(wcmatch(cadr ls_out)str_key)
                       (setq lst nil)
                     (setq lst(cdr lst)ls_out nil))
                   )
                 (if ls_out (vlax-vla-object->ename(caddr ls_out))))
               (vl-remove-if '(lambda(a)(/=(car a)"AcDbAlignedDimension"))ls_obj)
               )
              )

        
        (if(and vnam_text entna_dim)
            (setq ii -1
                  p(vlax-safearray->list(vlax-variant-value(vla-get-insertionpoint vnam_text)))
                  ls_dist
                  (mapcar
                   '(lambda(pd)
                      (setq ii(1+ ii))
                      (list(distance pd p)ii))
                   ls_pgrid_lefttop)
                  ls_dist(vl-sort ls_dist '(lambda(a b)(<(car a)(car b))))
                  ii(cadr(car ls_dist))
                  ls_gcode(entget entna_dim)
                  p0(cdr(assoc 13 ls_gcode))p1(cdr(assoc 14 ls_gcode))
                  ls_dwslice(cons(list ii p0 p1) ls_dwslice)
                  
                  ))
        )

      (if(= int_unit_plane 1)
          (setq p_scalebase
                (mapcar
                 '(lambda(func)
                    (apply 'min
                           (apply 'append
                                  (mapcar '(lambda(lst)
                                             (mapcar 'func (list(cadr lst)(caddr lst))))
                                          ls_dwslice)))
                    )
                 (list car cadr))
                p_scalebase(carxyz p_scalebase 0.)
                p_modelbase(getpoint
                            (mix_strasc(list 12514 12487 12523 36215 28857 12434 36984 25246 12375 12390 12367 12384 12373 12356 ))
                            p_scalebase)
                )
        
        (setq p_scalebase(list 0 0 0)
              p_modelbase(list 0 0 0)
              )
        )

      (setq ls_dwslice
            (mapcar
             '(lambda(lst / ls_p vec d0 d1)
                (setq ls_p
                      (if(= int_unit_plane 1)
                          (mapcar
                           '(lambda(p)
                              (mapcar '(lambda(a b c)(+ c(*(- a b)0.001)))p p_scalebase p_modelbase)
                              )
                           (cdr lst))
                        (cdr lst))
                      vec(unit_vector(mapcar '-(cadr ls_p)(car ls_p)))
                      d0(apply '+(mapcar '* vec(car ls_p)))
                      d1(apply '+(mapcar '* vec(cadr ls_p)))
                      )
                (list(car lst)vec d0 d1)
                )
             ls_dwslice)
            )
      
      
      (setq ls_ducterror(list))
      (mapcar
       '(lambda(lst / bool_loop )
          (setq str_name(car lst)vnam1(cadr lst)vnam2(caddr lst))
          (setq diam0(cdr(assoc str_name ls_duct_diam)))
          (if(or(null diam0)(= diam0 0.))T
            (progn
              
              (setq bool_loop T
                    ls_dummy ls_valgrid num_grid -1 bool_change T
                    ls_p1(vlax-safearray->list(vlax-variant-value(vla-get-coordinates vnam1)))
                    ls_p1(split_list
                          (if(=(vla-get-ObjectName vnam1)"AcDb3dPolyline")3
                            (if(=(vla-get-ObjectName vnam1)"AcDbPolyline")2))
                          ls_p1)
                    ls_p2(vlax-safearray->list(vlax-variant-value(vla-get-coordinates vnam2)))
                    ls_p2(split_list
                          (if(=(vla-get-ObjectName vnam2)"AcDb3dPolyline")3
                            (if(=(vla-get-ObjectName vnam2)"AcDbPolyline")2))
                          ls_p2)
                    
                    ls_p_side ls_p1 ls_p_plane ls_p2
                    x_min(apply 'min(mapcar 'car ls_p_side))
                    x_max(apply 'max(mapcar 'car ls_p_side))
                    y_min(apply 'min(mapcar 'cadr ls_p_side))
                    y_max(apply 'max(mapcar 'cadr ls_p_side))
                    
                    )
              
              (while(and bool_loop ls_dummy)
                (setq num_grid(1+ num_grid) lst(car ls_dummy)ls_dummy(cdr ls_dummy) )
                
                (setq scale_x_grid(caddr(car lst))xval_grid(cadddr(car lst))
                      scale_y_grid(caddr(cadr lst))yval_grid(cadddr(cadr lst))
                      )

                (setq lst(nth num_grid ls_rangegrid)
                      x_min_grid(car lst)x_max_grid(cadr lst)
                      y_min_grid(caddr lst)y_max_grid(cadddr lst)
                      )
                
                (if(or(and(<(*(- x_min x_min_grid)(- x_min x_max_grid))0)
                          (<(*(- y_min y_min_grid)(- y_min y_max_grid))0) )
                      (and(<(*(- x_max x_min_grid)(- x_max x_max_grid))0)
                          (<(*(- y_max y_min_grid)(- y_max y_max_grid))0) )
                      )
                    (setq bool_loop nil )
                  )
                
                (if(and bool_change bool_loop(null ls_dummy))
                    (setq bool_change nil ls_dummy ls_valgrid num_grid -1
                          ls_p_side ls_p2 ls_p_plane ls_p1
                          
                          x_min(apply 'min(mapcar 'car ls_p_side))
                          x_max(apply 'max(mapcar 'car ls_p_side))
                          y_min(apply 'min(mapcar 'cadr ls_p_side))
                          y_max(apply 'max(mapcar 'cadr ls_p_side))
                          
                          ))
                
                )
              
              (setq int_color(vla-get-color vnam1)
                    str_layer(vla-get-layer vnam1))
              
              (if bool_loop
                  (progn


                    
                    (setq ls_ducterror(cons str_name ls_ducterror))

                    )
                (progn
                  
                  (setq lst(nth num_grid ls_p_grid)
                        x_min_grid(apply 'min(mapcar 'car(car lst)))
                        y_min_grid(apply 'min(mapcar 'cadr(cadr lst)))
                        )
                  
                  (setq lst(cdr(assoc num_grid ls_dwslice))
                        vec_dire(car lst)dist_dire0(cadr lst)dist_dire1(caddr lst))

                  (setq ls_p_side
                        (mapcar
                         '(lambda(p / x y)
                            (setq x(+(*(-(car p)x_min_grid)scale_x_grid)xval_grid)
                                  y(+(*(-(cadr p)y_min_grid)scale_y_grid)yval_grid)
                                  )
                            (list x y)
                            )
                         ls_p_side)

                        )
                  
                  
                  (setq ls_p(mapcar '(lambda(p)(carxyz p 0.)) ls_p_plane)
                        ls_p_plane
                        (mapcar
                         '(lambda(pp / dd)
                            
                            (if(= int_unit_plane 1)
                                (setq pp(mapcar '(lambda(a b c)(+ c(*(- a b)0.001)))pp p_scalebase p_modelbase)))

                            (setq pp(car(project_to_ground
                                         (list(carxyz pp 0.))(list 0. 0. 1.) (list str_lasground height_ground)
                                         ))
                                  )
                            
                            (list(-(apply '+(mapcar '* vec_dire pp))dist_dire0)
                                 (- dist_dire1(apply '+(mapcar '* vec_dire pp)))
                                 pp)
                            
                            )
                         ls_p_plane)
                        
                        )
                  
                  ((lambda()

                     (setq i 0)
                     (while
                         (progn
                           (setq str_bname(strcat str_name "ROAD$"(itoa(setq i(1+ i)))))
                           (null
                            (vl-catch-all-error-p
                             (vl-catch-all-apply 'vla-Item(list vnam_blocktable str_bname))))
                           )
                       )
                     
                     (setq block(vla-Add vnam_blockTable(vlax-3d-point 0 0 0)str_bname)
                           ls_vla-release(cons block ls_vla-release))
                     

                     (setq bool_first T ls_int_node(list 0) int_node 0
                           ls_p(apply 'append
                                      (mapcar
                                       '(lambda(p1 p2 / d n v ls_out ls_int)
                                          (setq d(distance p1 p2)
                                                v(unit_vector(mapcar '- p2 p1))
                                                n(if(= pitch_project 0.)1
                                                   (1+(fix(/ d pitch_project))))
                                                d(/ d n)
                                                )
                                          (if bool_first
                                              (setq ls_int(inclist 0(1+ n))bool_first nil )
                                            (setq ls_int(inclist 1(1+ n))))
                                          
                                          (setq int_node(+ int_node n)
                                                ls_int_node(cons int_node ls_int_node)
                                                )
                                          (mapcar '(lambda(i)(mapcar '(lambda(a b)(+ a(* i d b))) p1 v))
                                                  ls_int)
                                          )
                                       ls_p(cdr ls_p)))
                           ls_p(project_to_ground ls_p(list 0. 0. 1.)(list str_lasground height_ground))
                           
                           )

                     (mapcar
                      '(lambda(n / p v)
                         (if(setq p(nth n ls_p))(setq v(vla-addcircle block (vlax-3d-point p)radius_node)) ))
                      ls_int_node)
                     (setq ls_p(apply 'append ls_p))
                     (setq array_p(vlax-make-safearray vlax-vbDouble(cons 0 (1-(length ls_p)))))
                     (vlax-safearray-fill array_p ls_p)
                     (setq vnam(vla-Add3dPoly block array_p))
                     (vla-put-color vnam int_color)
                     (vla-put-layer vnam str_layer)
                     (setq vnam(vla-InsertBlock
                                (vla-get-ModelSpace(vla-get-ActiveDocument(vlax-get-acad-object)))
                                (vlax-3d-point 0 0 0)str_bname 1 1 1 0)
                           )
                     (set_xda vnam(list(cons 1000 "PROJECT")
                                       (cons 1000 "PROJECT")(cons 1000 ""))
                              "terraduct3d")

                     ((lambda(v)
                        (vlax-release-object v)
                        (setq ls_vla-release(vl-remove v ls_vla-release)))
                      block)

                     
                     )
                   )
                  
                  
                  (setq ls_p_duct(list)ls_pmesh(list)ls_pbar(list))

                  (cond
                   ((< diam0 0.)
                    (setq elev0(/(apply '+(mapcar 'cadr ls_p_side))(length ls_p_side))
                          ls_p(mapcar 'caddr ls_p_plane))

                    ((lambda( / bool_loop)
                       (setq bool_loop T)
                       (while bool_loop
                         (setq bool_loop nil)
                         (setq ls_p(mapcar '(lambda(p1 p0)
                                              (if(<(distance p1 p0)1e-6)
                                                  (progn
                                                    (setq bool_loop T)
                                                    nil)
                                                p0))
                                           (cons(last ls_p)ls_p)ls_p)
                               ls_p(vl-remove nil ls_p)
                               )
                         )
                       ))
                    
                    (setq s_area(apply '+
                                       (mapcar '(lambda(p0 p1)
                                                  (* 0.5(+(cadr p0)(cadr p1))(-(car p1)(car p0))))
                                               ls_p(append(cdr ls_p)(list(car ls_p)))))
                          )
                    (if(< s_area 0)(setq ls_p(reverse ls_p)))
                    
                    
                    (setq ls_entna
                          (code_loft_solid
                           (mapcar '(lambda(hh)(mapcar '(lambda(lst)(carxyz lst hh))ls_p))
                                   (list elev0(+ elev0 diam0)))
                           nil nil)
                          vnam(vlax-ename->vla-object(car ls_entna))
                          )
                    (vla-put-layer vnam str_layer)
                    (vla-put-color vnam int_color)
                    
                    
                    
                    )
                   
                   ((if(=(length ls_p_side)(length ls_p_plane))
                        (if(apply 'and
                                  (mapcar '(lambda(a b)(<(abs(-(car a)(car b)))1e-3))
                                          ls_p_plane ls_p_side)
                                  )
                            T
                          (if(apply 'and
                                    (mapcar '(lambda(a b)(<(abs(-(cadr a)(car b)))1e-3))
                                            ls_p_plane ls_p_side)
                                    )
                              T
                            (progn
                              (mapcar '(lambda(a b)
                                         (princ(list(car a)(cadr a)(car b))))
                                      ls_p_plane ls_p_side)
                              (princ str_name)
                              ;;(getint)
                              nil
                              )))
                      )

                    (setq ls_dummy
                          (mapcar '(lambda(p_plane p_side / zz p)
                                     (setq p(caddr p_plane)zz(caddr p))
                                     (list p (carxyz p(+ zz(cadr p_side))))
                                     )
                                  ls_p_plane ls_p_side)
                          p-1 nil radius_arc diam0
                          ls_p_duct(list)
                          
                          )



                    
                    (while ls_dummy
                      (setq lst(car ls_dummy)p0(cadr lst)p00(car lst)
                            lst(cadr ls_dummy)p1(cadr lst)p10(car lst)ls_dummy(cdr ls_dummy)
                            ls_add(list)pc nil)
                      
                      (if p1
                          (progn
                            (setq vec2(unit_vector(mapcar '- p1 p0)) )
                            (if p-1
                                (setq cosa(-(apply '+(mapcar '* vec1 vec2)))
                                      d_sepa(* radius_arc(sqrt(/(- 1. cosa)(+ 1. cosa))))
                                      d_cen(/ d_sepa(- 1. cosa))
                                      pc(mapcar '(lambda(a b c)(+ a(* d_cen b)(* d_cen c)))
                                                p0 vec1 vec2)
                                      p(mapcar '(lambda(a b)(+ a(* d_sepa b)))p0 vec1)
                                      p1(mapcar '(lambda(a b)(+ a(* d_sepa b)))p0 vec2)
                                      ls_add(list p-1 p
                                                  pc p1
                                                  (mapcar '(lambda(a b)(+ a(* radius_arc b)))
                                                          pc(unit_vector(mapcar '- p0 pc)))
                                                  )
                                      p-1 p1 
                                      )
                              
                              (setq p-1 p0 ))
                            
                            )
                        (setq ls_add(list p-1 p0)
                              vec1(unit_vector(mapcar '- p-1 p0)))
                        )

                      ;; (if(caddr ls_add)
                      ;;     (mapcar
                      ;;      '(lambda(p i)(entmake(list(cons 0 "CIRCLE")(cons 10 p)(cons 40 0.1)(cons 62 i))))
                      ;;      ls_add(list 1 2 3 4 5 6 7)))
                      ;; (getint)

                      (if ls_add
                          (progn
                            (setq ls_p_duct(cons ls_add ls_p_duct)
                                  vec1(mapcar '- vec1)
                                  )
                            
                            (if ls_pbar T
                              (setq ls_pbar(list(list(car ls_add)nil vec1))
                                    ls_pmesh(list(list(car ls_add) vec1))
                                    ))

                            
                            ;; (setq p(if ls_pbar(caar ls_pbar)p_line0))
                            
                            ;; (if(<(apply '+(mapcar '* vec0 vec14))0)(setq vec0(mapcar '- vec0)))
                            ;; (if(>(apply '+(mapcar '* vec1 vec13))0)(setq vec1(mapcar '- vec1)))
                            ;; (if(<(apply '+(mapcar '*(mapcar '- p13 p)vec0))-1e-8)
                            ;;     (setq ls_pbar(cons(list p13 nil vec0)(cdr ls_pbar)))
                            ;;   ;; (if(= int_protectcon_temp 2)T

                            ((lambda( / p d n i dd pm)
                               (setq p(car ls_add)
                                     d(distance p(cadr ls_add)) n(1+(fix(/ d pitch_mesh))) d(/ d n)
                                     dd 0.)
                               (while(>(setq n(1- n))-1)
                                 (setq dd(+ dd d)
                                       pm(mapcar '(lambda(a b)(+ a(* dd b)))p vec1)
                                       ls_pmesh(cons(list pm vec1)ls_pmesh)
                                       )
                                 )
                               ))
                            
                            (if pc
                                ((lambda( / d n i ang vec_x vec_y pm dd c s v)
                                   (setq rr radius_arc
                                         p13(cadr ls_add)p14(cadddr ls_add)
                                         vec13(unit_vector(mapcar '- p13 pc))
                                         vec14(unit_vector(mapcar '- p14 pc))
                                         )
                                   
                                   (setq ls_pbar(cons(list p13 pc vec1)ls_pbar)
                                         ls_pbar(cons(list p14 nil vec2)ls_pbar)
                                         )
                                   
                                   (setq ang(atan(distance(cross_product vec13 vec14)(list 0 0 0))
                                                 (apply '+(mapcar '* vec13 vec14)))
                                         vec_x(mapcar '(lambda(a)(* a rr))vec13)
                                         vec_y(mapcar '(lambda(a)(* a rr))vec1)
                                         d(* rr ang) n(1+(fix(/ d(min(* 0.5 rr) pitch_mesh))))
                                         d(/ ang n)
                                         ang 0.)
                                   
                                   (while(>(setq n(1- n))-1)
                                     (setq ang(+ ang d)c(cos ang)s(sin ang)
                                           v(mapcar '(lambda(x y)(+ (* -1 s x)(* c y)))vec13 vec1)
                                           pm(mapcar '(lambda(a x y)(+ a(* c x)(* s y)))pc vec_x vec_y)
                                           ls_pmesh(cons(list pm v)ls_pmesh)
                                           )
                                     )
                                   ))
                              )
                            
                            ))
                      
                      (setq vec1(mapcar '- vec2))
                      )

                    (setq ls_pbar(cons(list p0 nil(caddr(car ls_pbar)))ls_pbar))
                    

                    (setq ls_p_duct(reverse ls_p_duct))

                    
                    ;; (setq vnam_blockTable(vla-get-blocks(vla-get-ActiveDocument (vlax-get-acad-object)))
                    ;;       ls_vla-release(list vnam_blockTable ));;errorよりあとにやる

                    (while(null(vl-catch-all-error-p
                                (setq block(vl-catch-all-apply
                                            'vla-Item(list(vla-get-blocks(vla-get-ActiveDocument (vlax-get-acad-object)))
                                                          str_name)))))
                      (setq str_name
                            (if(setq num(vl-string-search "$" str_name))
                                (strcat(substr str_name 1 num)"$"
                                       (itoa(1+(atoi(substr str_name(+ 2 num))))))
                              (strcat str_name "$0"))
                            )
                      )

                    (setq block(vla-Add(vla-get-blocks(vla-get-ActiveDocument (vlax-get-acad-object)))
                                       (vlax-3d-point 0 0 0)str_name) )
                    (setq ls_vla-release(cons block ls_vla-release))

                    (setq int_duct -1 ls_vnam_copy(list) )
                    (mapcar
                     '(lambda(ls_p / p00 p01 p10 p11 p0 p1 pc pa pr)
                        (mapcar 'set '(p0 p1 pc pa pr)ls_p)
                        (setq p00(car(project_to_ground
                                      (list(carxyz p0 0.))(list 0. 0. 1.) (list str_lasground height_ground)
                                      ))
                              p10(car(project_to_ground
                                      (list(carxyz p1 0.))(list 0. 0. 1.) (list str_lasground height_ground)
                                      ))
                              )
                        
                        (setq int_duct(1+ int_duct))
                        (setq vec_line(unit_vector(carxyz(mapcar '- p1 p0)0.)))
                        (mapcar
                         '(lambda(lst ii / p0 p1 h)
                            
                            (setq p0(car lst)p1(cadr lst)h str_bname
                                  str_level(depth_level_str p0 p1)
                                  entna(make_2pdimension
                                        nil(list p0 p1 vec_line
                                                 (apply '+(mapcar '* vec_line p0))
                                                 nil(* 0.5 pi)
                                                 0. str_level
                                                 str_dimstyle_ductlevel
                                                 )
                                        )
                                  vnam(vlax-ename->vla-object entna)
                                  ls_vnam_copy(cons vnam ls_vnam_copy)
                                  )
                            (vla-put-Arrowhead1Type vnam 13)
                            (vla-put-Arrowhead2Type vnam 6)
                            (vla-put-ExtLine1Suppress vnam -1)
                            (vla-put-ExtLine2Suppress vnam -1)
                            (vla-put-HorizontalTextPosition vnam 3)
                            ;;(if(= int_invisible_annotation 1)(vla-put-visible vnam :vlax-false))
                            (vla-put-color vnam int_colductdim)
                            (set_xda vnam(list(cons 1000 "DEPTH")
                                              (cons 1000 "NUM")(cons 1071 int_duct)
                                              (cons 1000 "SIDE")(cons 1071 ii)
                                              (cons 1000 "ROAD")(cons 1000 h)
                                              )
                                     "terraduct3d")
                            )

                         (list(list p00 p0) (list p10 p1) )
                         
                         ;; (mapcar '(lambda(p)
                         ;;            (list
                         ;;             (car(project_to_ground
                         ;;                  (list p)(list 0. 0. 1.)(list nil 0.)
                         ;;                  ;;(list str_lasground height_ground)
                         ;;                  ))
                         ;;             p)
                         ;;            )
                         ;;         (list p0 p1))
                         (list 0 1))
                        
                        (setq vnam
                              (vla-addline
                               (vla-get-modelspace(vla-get-activedocument(vlax-get-acad-object)))
                               (vlax-3d-point p0)(vlax-3d-point p1))
                              ls_vnam_copy(cons vnam ls_vnam_copy)
                              )
                        (vla-put-color vnam int_colductdim)
                        (set_xda vnam(list(cons 1000 "LINE")
                                          (cons 1000 "NUM")(cons 1071 int_duct))
                                 "terraduct3d")

                        
                        (if pc
                            (progn
                              (setq rr radius_arc
                                    vec_normal(unit_vector
                                               (cross_product
                                                (mapcar '- pa pc)(mapcar '- p1 pc) ))
                                    dist_normal(apply '+(mapcar '* pc vec_normal))
                                    )
                              
                              (mapcar
                               '(lambda(ii p15 p13 p14 p16)
                                  (setq entna(make_arcdimension
                                              nil(list p15 p13 p14 p16 rr
                                                       vec_normal dist_normal
                                                       (strcat "R="(if(< rr 1e-8)(chr 8734)
                                                                     (as-numstr rr )))
                                                       str_dimstyle_ductlevel
                                                       )
                                              )
                                        vnam(vlax-ename->vla-object entna)
                                        ls_vnam_copy(cons vnam ls_vnam_copy)
                                        )
                                  (if(= int_invisible_annotation 1)(vla-put-visible vnam :vlax-false))
                                  (vla-put-color vnam int_colductdim)
                                  (arc2_dimstyle vnam)
                                  
                                  (set_xda vnam(list(cons 1000 "ARC")
                                                    (cons 1000 "NUM")(cons 1071 int_duct)
                                                    (cons 1000 "SIDE")(cons 1071 ii)
                                                    (cons 1000 "RADIUS")(cons 1040 rr)
                                                    )
                                           "terraduct3d")

                                  )
                               (list 0 1) (list pc pc) (list p1 pa) (list pa pa) (list pr pa)
                               )
                              ) )


                        )
                     ls_p_duct )
                    
                    
                    (setq ls_pcenterline(mapcar 'car(reverse ls_pmesh)))

                    (if(= str_ductsolidmesh "1")
                        (progn
                          (setq ls_pbar(reverse ls_pbar)
                                entna(bendpipe_lwpsld
                                      (* 0.5 diam0)ls_pbar (getvar "CLAYER") nil)
                                vnam(vlax-ename->vla-object entna)
                                )
                          )
                      (progn
                        (setq numy 32
                              ls_intmesh(inclist 0 numy)
                              ang_d(/(* 2. pi)numy)
                              r(* 0.5 diam0)
                              vecxp nil vecyp nil
                              )
                        
                        (setq ls_pduct
                              (mapcar
                               '(lambda(lst / p v vecx vecy)
                                  (setq p(car lst)v(cadr lst)
                                        v(unit_vector v )
                                        vecx(trans-x(list 1 0 0)v(list 0 0 1))
                                        vecy(trans-x(list 0 1 0)v(list 0 0 1))
                                        )
                                  
                                  (if(if vecxp(>(apply '+(mapcar '* vecx vecxp))0)T)T
                                    (setq vecx vecxp))
                                  (setq vecxp vecx)
                                  (if(<(caddr vecy)0)(setq vecy(mapcar '- vecy)))
                                  (mapcar '(lambda(i / c s)
                                             (setq c(cos(* ang_d i))s(sin(* ang_d i)))
                                             (mapcar '(lambda(a x y)(+(* r c x)(* r s y)a))
                                                     p vecx vecy))
                                          ls_intmesh)
                                  )
                               (reverse ls_pmesh)
                               )
                              
                              numx(length ls_pduct)
                              ls_p(apply 'append(apply 'append ls_pduct))
                              )
                        
                        (setq array_mesh(vlax-make-safearray vlax-vbDouble(cons 0(1-(length ls_p)))))
                        (vlax-safearray-fill array_mesh ls_p)
                        (setq vnam
                              (vla-Add3DMesh
                               (vla-get-ModelSpace(vla-get-ActiveDocument (vlax-get-acad-object)))
                               numx numy array_mesh)
                              
                              )
                        (vla-put-nclose vnam :vlax-true)

                        )
                      )

                    (vla-put-color vnam int_color)
                    (vla-put-layer vnam str_layer)
                    (setq ls_vnam_copy(cons vnam ls_vnam_copy))
                    
                    (set_xda vnam(list(cons 1000 "DUCTSOLID")
                                      (cons 1000 "DIAM")(cons 1040 diam0)
                                      )
                             "terraduct3d")
                    
                    (setq ls_p(apply 'append ls_pcenterline)
                          array_p(vlax-make-safearray vlax-vbDouble(cons 0(1-(length ls_p)))))
                    (vlax-safearray-fill array_p ls_p)
                    (setq vnam(vla-Add3dPoly
                               (vla-get-ModelSpace(vla-get-ActiveDocument(vlax-get-acad-object)))
                               array_p))
                    (setq ls_vnam_copy(cons vnam ls_vnam_copy))
                    (set_xda vnam(list(cons 1000 "CENTERLINE"))"terraduct3d")
                    
                    
                    
                    (vla-copyobjects
                     (vla-get-ActiveDocument(vlax-get-acad-object))
                     (vlax-make-variant
                      (vlax-safearray-fill
                       (vlax-make-safearray
                        vlax-vbObject(cons 0(1-(length ls_vnam_copy))) )
                       ls_vnam_copy)
                      )
                     block)

                    
                    (setq vnam(vla-InsertBlock
                               (vla-get-ModelSpace(vla-get-ActiveDocument(vlax-get-acad-object)))
                               (vlax-3d-point 0 0 0)str_name 1 1 1 0)
                          )
                    (set_xda vnam(list(cons 1000 "DUCTBLOCK"))"terraduct3d")
                    
                    (mapcar '(lambda(v)
                               (vla-delete v)
                               (exckillobj v)
                               )
                            ls_vnam_copy)
                    
                    
                    ;; (setq ls_p(apply 'append ls_p_duct) )
                    ;; (setq array_p(vlax-make-safearray vlax-vbDouble(cons 0 (1-(length ls_p)))))
                    ;; (vlax-safearray-fill array_p ls_p)
                    ;; (setq vnam(vla-Add3dPoly
                    ;;            (vla-get-ModelSpace(vla-get-ActiveDocument(vlax-get-acad-object)))
                    ;;            array_p))
                    ;; (vla-put-layer vnam str_layer)
                    ;; (vla-put-color vnam int_color)
                    
                    )
                   (T

                    (setq ls_ducterror(cons str_name ls_ducterror))
                    
                    )
                   )
                  

                  ))
              ))
          
          )
       ls_dwduct)


      
      (if ls_ducterror
          (alert(strcat "nomodeling:"(vl-princ-to-string ls_ducterror))))
      
      (x-alert(list "FINISHED"))
      ))
  (progn)
  )

;;=====================================================================
;; 円弧2本(交差/ねじれ)の限界(limit)計算
;;   insertarc(func_insertarc_initial)と refreshground の再構築で
;;   同じ計算が別々に書かれていたものを統合した。
;;
;;   前提 : 呼び出し前に文脈がグローバルに設定されていること
;;     共通   : bool_linetype radius_arcmove p_line00〜p_line11
;;              vec_line0 vec_line1 vec_normal dist_normal length_s
;;     交差(1): vec_nline0 vec_nline1 p_crossx も必要
;;   結果 : 次のグローバルへ置く
;;     ls_limit0 ls_limit1 p_limit0 p_limit1 p_center_limit00〜11
;;     交差(1)では dist_limit00〜11 も
;;   引数 :
;;     tol     : ねじれ探索の収束判定(従来値 1e-8)
;;     num_cap : ねじれ探索の反復上限(収束しない条件で固まらないため)
;;   平行(bool_linetype 0)には限界が無いので何もしない
;;=====================================================================
;;円弧寸法の "R=..." 表示文字列(半径が無限大相当のときは∞)
(defun arc2_dimtext( rr p1 p2 / )
  (strcat "R="(if(<(distance p1 p2)1e-8)(chr 8734)(rtos rr 2 3))))

;;円弧寸法の見た目の定型(矢印19・補助線抑制・文字位置)。5箇所で同文だったものを統合
(defun arc2_dimstyle( vnam / )
  (vla-put-Arrowhead1Type vnam 19)
  (vla-put-Arrowhead2Type vnam 19)
  (vla-put-ExtLine1Suppress vnam -1)
  (vla-put-ExtLine2Suppress vnam -1)
  (vla-put-HorizontalTextPosition vnam 3)
  (vla-put-TextInsideAlign vnam 0)
  (vla-put-VerticalTextPosition vnam 2)
  (princ))

(defun arc2_limits( tol num_cap / delta_arc bool_loop d p_temp lst p
                                  num_limitsearch )
  (setq ls_limit0 nil ls_limit1 nil p_limit0 nil p_limit1 nil)
  (cond
   ((= bool_linetype 1)
    (setq p_center_limit00
          (3dcross_3pl vec_normal dist_normal
                       vec_nline0(+(apply '+(mapcar '* p_crossx vec_nline0))
                                   (* -1 radius_arcmove))
                       vec_nline1(+(apply '+(mapcar '* p_crossx vec_nline1))
                                   (* 2 radius_arcmove))
                       )
          ls_limit0
          (cal_arcposition radius_arcmove nil p_center_limit00 p_crossx
                           vec_line0 vec_nline0 vec_line1 vec_nline1)
          p_center_limit10(nth 2 ls_limit0)
          )
    (setq p_center_limit11
          (3dcross_3pl vec_normal dist_normal
                       vec_nline0(+(apply '+(mapcar '* p_crossx vec_nline0))
                                   (* 2 radius_arcmove))
                       vec_nline1(+(apply '+(mapcar '* p_crossx vec_nline1))
                                   (* -1 radius_arcmove))
                       )
          ls_limit1
          (cal_arcposition radius_arcmove nil p_center_limit11 p_crossx
                           vec_line1 vec_nline1 vec_line0 vec_nline0)
          p_center_limit01(nth 2 ls_limit1)

          dist_limit00(apply '+(mapcar '* p_center_limit00 vec_line0))
          dist_limit01(apply '+(mapcar '* p_center_limit01 vec_line0))
          dist_limit10(apply '+(mapcar '* p_center_limit10 vec_line1))
          dist_limit11(apply '+(mapcar '* p_center_limit11 vec_line1))
          )
    )
   ((= bool_linetype 2)
    ;;起点側 : 円弧の起点が p_line01 に一致する接点位置を探す
    (setq delta_arc(* -0.1 radius_arcmove) bool_loop T d 0
          num_limitsearch num_cap)
    (while bool_loop
      (setq d(+ d delta_arc)
            p_temp(mapcar '(lambda(a b)(+ a(* d b)))p_line01 vec_line0)
            lst(cal_twisttangent
                radius_arcmove p_temp
                p_line00 p_line01 p_line10 p_line11 vec_line0 vec_line1 length_s)
            )
      (if(setq p(cadar lst))
          (cond
           ((<(distance p p_line01)tol)
            (setq ls_limit0 lst p_limit0 p_temp bool_loop nil))
           (T
            (setq ls_limit0 lst p_limit0 p_temp)
            (if(>(*(apply '+(mapcar '*(mapcar '- p p_line01)vec_line0))delta_arc)0)
                (setq delta_arc(* -0.1 delta_arc)) )
            )
           )
        (if(null ls_limit0)(setq delta_arc(* -1.1 delta_arc))
          (setq bool_loop nil))
        )
      ;;収束しない条件でも必ず抜ける(反復上限)
      (if(<(setq num_limitsearch(1- num_limitsearch))0)(setq bool_loop nil))
      )

    ;;終点側 : 線を入れ替えて同じ探索
    (setq delta_arc(* -0.1 radius_arcmove) bool_loop T d 0
          num_limitsearch num_cap)
    (while bool_loop
      (setq d(+ d delta_arc)
            p_temp(mapcar '(lambda(a b)(+ a(* d b)))p_line10 vec_line1)
            lst(cal_twisttangent
                radius_arcmove p_temp
                p_line10 p_line11 p_line00 p_line01 vec_line1 vec_line0 length_s)
            )
      (if(setq p(cadar lst))
          (cond
           ((<(distance p p_line10)tol)
            (setq ls_limit1 lst bool_loop nil p_limit1 p_temp))
           (T
            (setq ls_limit1 lst p_limit1 p_temp)
            (if(>(*(apply '+(mapcar '*(mapcar '- p p_line10)vec_line1))delta_arc)0)
                (setq delta_arc(* -0.1 delta_arc)) )
            )
           )
        (if(null ls_limit1)(setq delta_arc(* -1.1 delta_arc))
          (setq bool_loop nil))
        )
      (if(<(setq num_limitsearch(1- num_limitsearch))0)(setq bool_loop nil))
      )

    (setq p_center_limit00(caar ls_limit0)
          p_center_limit01(caadr ls_limit0)
          p_center_limit10(caadr ls_limit1)
          p_center_limit11(caar ls_limit1)
          )
    )
   )
  (princ))

(defun func_insertarc_initial( / bool_loop num_limitsearch )
  (mapcar 'set '(vec_normal dist_normal radius_arcmove
                            p_line00 p_line01 p_line10 p_line11
                            vec_line0 vec_line1 length_s
                            bool_linetype lst)
          ls_arcmove)


  (setq ls_arc_temp nil)
  (setq point_decide nil ls_limit0 nil ls_limit1 nil
        p_limit0 nil p_limit1 nil
        vec_normal1 nil dist_normal1 nil)
  (cond
   ((= bool_linetype 0)
    
    (setq vec_linenormal(car lst) dist_linenormal(cadr lst))
    (if(= int_editarcposition_temp 3)
        (setq radius_arcmove(max radius_bend_temp(* 0.5 dist_linenormal))
              int_editarcposition_temp 1 ))
    (setq dist_lineparallel
          (sqrt(* dist_linenormal(-(* 2. radius_arcmove)dist_linenormal)))
          )
    
    )
   ((= bool_linetype 1)
    
    (mapcar
     'set '(vec_nline0 vec_nline1 p_centerx p_arcstartx p_arcendx p_arcwayx p_crossx)
     lst)


    (if(= int_editarcposition_temp 3)
        ((lambda( / vec_normal vec_nline0 vec_nline1)
           (setq bool_distline T radius_limit radius_bend_temp num_limit 100
                 vec_normal(unit_vector(cross_product vec_line0 vec_line1))
                 vec_nline0(cross_product vec_line0 vec_normal)
                 vec_nline1(cross_product vec_normal vec_line1)
                 )
           
           (while(= int_editarcposition_temp 3)
             (setq p_h00(mapcar '(lambda(a b)(+ a(* radius_arcmove b)))
                                p_line01 vec_nline0)
                   p_h01(mapcar '(lambda(a b)(+ a(* -1 radius_arcmove b)))
                                p_line01 vec_nline0)
                   p_h10(mapcar '(lambda(a b)(+ a(* radius_arcmove b)))
                                p_line10 vec_nline1)
                   p_h11(mapcar '(lambda(a b)(+ a(* -1 radius_arcmove b)))
                                p_line10 vec_nline1)
                   dist_line_tan
                   (-(min(distance p_h00 p_h11)(distance p_h01 p_h10))
                     (* 2 radius_arcmove))
                   )
             
             ;;todo円弧の作り方を変えるか
             (setq num_limit(1- num_limit))
             (cond
              ((< num_limit 0)
               (setq int_editarcposition_temp 1)
               )
              ((<(abs dist_line_tan)1e-8)
               (setq int_editarcposition_temp 1))
              ((> dist_line_tan 0.)
               (if(< delta_arcmove 0)(setq delta_arcmove(* -0.1 delta_arcmove)))
               (setq radius_arcmove(+ radius_arcmove delta_arcmove))
               )
              
              ((<(- radius_arcmove radius_limit)1e-8)
               (setq radius_arcmove radius_limit int_editarcposition_temp 1))
              (T
               (if(> delta_arcmove 0)(setq delta_arcmove(* -0.1 delta_arcmove)))
               (setq radius_arcmove(+ radius_arcmove delta_arcmove)))
              )
             )
           (setq radius_arcmove
                 (atof(rtos radius_arcmove 2 int_unitarcautoma)))
           
           ) ))
    
    ;;限界計算は arc2_limits に統合した
    (arc2_limits 1e-8 1000)
    )
   ((= bool_linetype 2)

    ;; (mapcar
    ;;  'set '(vec_nline0 vec_nline1 p_centerx p_arcstartx p_arcendx p_arcwayx p_crossx)
    ;;  lst)
    (setq vec_normal(unit_vector(cross_product(mapcar '- p_line10 p_line01)vec_line0))
          dist_normal(apply '+(mapcar '* vec_normal p_line01))
          ;;終点側の基準平面(線1と結線を含む)。MOVE の投影とキー51の再現に使う
          vec_normal1(unit_vector(cross_product(mapcar '- p_line01 p_line10)vec_line1))
          dist_normal1(apply '+(mapcar '* vec_normal1 p_line10)))

    (setq bool_distline T radius_limit radius_bend_temp num_limit 100
          )
    
    (if(= int_editarcposition_temp 3)
        (progn
          (setq length_arc_min 0
                vec_ends(mapcar '- p_line10 p_line01)
                length_arc_max(distance p_line01 p_line10)
                variable_a(expt length_arc_max 2)
                variable_b(* 2.(apply '+(mapcar '* vec_ends vec_line0)))
                variable_c(* 2.(apply '+(mapcar '* vec_ends vec_line1)))
                variable_d(* 2.(1+(apply '+(mapcar '* vec_line0 vec_line1))))
                )
          
          (while(= int_editarcposition_temp 3)
            
            (setq length_arc_x
                  (/(+ variable_a(* length_arc_min variable_b))
                    (+ variable_c(* length_arc_min variable_d)))
                  vec_common
                  (mapcar '(lambda(a b c)
                             (+ a(* length_arc_min b)(* -1. length_arc_x c)))
                          vec_ends vec_line0 vec_line1)
                  vec_common(unit_vector vec_common)
                  radius1(apply '+(mapcar '* vec_line0 vec_common))
                  radius1(* length_arc_min(sqrt(/(- 1 radius1)(+ 1 radius1))))
                  radius2(apply '+(mapcar '* vec_line1 vec_common))
                  radius2(* length_arc_x(sqrt(/(+ 1 radius2)(- 1 radius2))))
                  dist_line_tan(- radius1 radius2)
                  )

            (setq num_limit(1- num_limit))
            (cond
             ((< num_limit 0)(setq int_editarcposition_temp 1))
             ((<(abs dist_line_tan)1e-8)
              (setq radius_arcmove(max radius_arcmove radius1))
              (setq int_editarcposition_temp 1))
             ((< dist_line_tan 0.)
              (if(< delta_arcmove 0)(setq delta_arcmove(* -0.1 delta_arcmove)))
              (setq length_arc_min(+ length_arc_min delta_arcmove))
              )
             (T
              (if(> delta_arcmove 0)(setq delta_arcmove(* -0.1 delta_arcmove)))
              (setq length_arc_min(+ length_arc_min delta_arcmove)))
             )
            )

          (setq radius_arcmove
                (atof(rtos radius_arcmove 2 int_unitarcautoma)))
          
          
          ;; (while(= int_editarcposition_temp 3)
          ;;   (setq delta_arc(* -0.1 radius_arcmove) bool_loop T d 0 ls_limit0(list))
          ;;   (setq num_limit2 100)
          ;;   (while bool_loop
          ;;     (setq d(+ d delta_arc)
          ;;           p_temp(mapcar '(lambda(a b)(+ a(* d b)))p_line01 vec_line0)
          ;;           lst(cal_twisttangent
          ;;               radius_arcmove p_temp
          ;;               p_line00 p_line01 p_line10 p_line11 vec_line0 vec_line1 length_s)
          ;;           num_limit2(1- num_limit2)
          ;;           )
          ;;     (if(setq p(cadar lst))
          ;;         (cond
          ;;          ((<(distance p p_line01)1e-6)
          ;;           (setq ls_limit0 lst p_limit0 p_temp bool_loop nil))
          ;;          (T
          ;;           (setq ls_limit0 lst p_limit0 p_temp)
          ;;           (if(>(*(apply '+(mapcar '*(mapcar '- p p_line01)vec_line0))delta_arc)0)
          ;;               (setq delta_arc(* -0.1 delta_arc)) )
          ;;           )
          ;;          )
          ;;       (if(< num_limit2 0)(setq bool_loop nil)
          ;;         (if(null ls_limit0)(setq delta_arc(* -1. delta_arc))
          ;;           (setq bool_loop nil)))
          ;;       )
          ;;     )
          
          ;;   (setq dist_line_tan
          ;;         (if bool_distline
          ;;             (apply '+(mapcar '*(mapcar '-(nth 1(car ls_limit0)) p_line01) vec_line0))
          ;;           (apply '+(mapcar '*(mapcar '-(nth 1(cadr ls_limit0)) p_line10) vec_line1)))
          ;;         )

          
          
          ;;   (setq num_limit(1- num_limit))
          ;;   (cond
          ;;    ((< num_limit 0)(setq int_editarcposition_temp 1))
          ;;    ((<(abs dist_line_tan)1e-8)
          ;;     (if bool_distline(setq bool_distline nil radius_limit radius_arcmove
          ;;                            delta_arcmove(* 0.1 radius_arcmove) )
          ;;       (setq int_editarcposition_temp 1)))
          ;;    ((< dist_line_tan 0.)
          ;;     (if(< delta_arcmove 0)(setq delta_arcmove(* -0.1 delta_arcmove)))
          ;;     (setq radius_arcmove(+ radius_arcmove delta_arcmove))
          ;;     )
          
          ;;    ((<(- radius_arcmove radius_limit)1e-8)
          ;;     (setq radius_arcmove radius_limit int_editarcposition_temp 1))
          ;;    (T
          ;;     (if(> delta_arcmove 0)(setq delta_arcmove(* -0.1 delta_arcmove)))
          ;;     (setq radius_arcmove(+ radius_arcmove delta_arcmove)))
          ;;    )
          ;;   )
          
          ))

    ;;限界計算(2方向の探索と p_center_limit の設定)は arc2_limits に統合した。
    ;;※旧コードにあった p_tangent0 と dist_limit00〜11 はねじれでは未使用のため廃止
    (arc2_limits 1e-8 1000)

    )
   )
  )

(defun func_insertarc_move( p sym int_temp / lst bool ls_p px vec pc pco pho)
  (setq bool(= int_temp 0))
  (cond
   ((= bool_linetype 0)
    ;;平行
    (setq px(mapcar '(lambda(a x y)
                       (+ a(*(if bool 1 -1)dist_lineparallel x)
                          (*(if bool 1 -1)dist_linenormal y)))
                    p vec_line1 vec_linenormal)
          pc(mapcar '(lambda(a y)(+ a(*(if bool 1 -1)radius_arcmove y)))
                    p vec_linenormal)
          pco(mapcar '(lambda(a b)(+(- a)(* 2. b)))pc px)
          pho(mapcar '(lambda(a y)(+ a(*(if bool 1 -1)radius_arcmove y)))
                     pco vec_linenormal)
          ls_p
          (if bool(list(list pc p px vec_normal)(list pco px pho vec_normal) )
            (list(list pco pho px vec_normal)(list pc px p vec_normal)))
          )

    (set sym
         (mapcar
          '(lambda(lst / pc p0 p1 p2)
             (setq pc(car lst)p0(cadr lst)p1(caddr lst)
                   p2(mapcar '(lambda(a b)(+ a(* radius_arcmove b)))
                             pc(unit_vector(mapcar '(lambda(a b c)(+ a b(* -2 c)))
                                                   p0 p1 pc)))
                   )
             (list pc p0 p1 p2 vec_normal))
          ls_p)
         )
    
    )
   
   ((= bool_linetype 1)
    ;;交差
    (setq d(apply '+(mapcar '* p(if bool vec_line0 vec_line1)))
          ls_p
          (if bool
              (cond
               ((> d dist_limit00)
                (mapcar '(lambda(lst)(mapcar '(lambda(i)(nth i ls_limit0))lst))
                        (list(list 0 1 4)(list 2 4 3))) )
               ((< d dist_limit01)
                (mapcar '(lambda(lst)(mapcar '(lambda(i)(nth i ls_limit1))lst))
                        (list(list 2 3 4)(list 0 4 1))) )
               (T
                (setq bool_limit T
                      lst(cal_arcposition
                          radius_arcmove p nil p_crossx
                          vec_line0 vec_nline0 vec_line1 vec_nline1)
                      )
                (mapcar '(lambda(x)(mapcar '(lambda(i)(nth i lst))x))
                        (if(caddr lst) (list(list 0 1 4)(list 2 4 3))
                          (list(list 0 1 4)(list 0 4 4))))
                )
               )
            
            (cond
             ((< d dist_limit10)
              (mapcar '(lambda(lst)(mapcar '(lambda(i)(nth i ls_limit0))lst))
                      (list(list 0 1 4)(list 2 4 3))) )
             ((> d dist_limit11)
              (mapcar '(lambda(lst)(mapcar '(lambda(i)(nth i ls_limit1))lst))
                      (list(list 2 3 4)(list 0 4 1))) )
             (T
              ;;bool_limi は bool_limit の書き損じだった。
              ;;このせいで終点側の中間域で仮寸法が更新されず、表示が古いままだった
              (setq bool_limit T
                    lst(cal_arcposition
                        radius_arcmove p nil p_crossx
                        vec_line1 vec_nline1 vec_line0 vec_nline0)
                    )
              
              (mapcar '(lambda(x)(mapcar '(lambda(i)(nth i lst))x))
                      (if(caddr lst) (list(list 2 3 4)(list 0 4 1))
                        (list(list 0 4 1)(list 0 1 1))))
              )
             )
            )
          )
    
    (set sym
         (mapcar
          '(lambda(lst / pc p0 p1 p2)
             (setq pc(car lst)p0(cadr lst)p1(caddr lst)
                   p2(mapcar '(lambda(a b)(+ a(* radius_arcmove b)))
                             pc(unit_vector(mapcar '(lambda(a b c)(+ a b(* -2 c)))
                                                   p0 p1 pc)))
                   )
             (list pc p0 p1 p2 vec_normal))
          ls_p)
         )

    )

   ((= bool_linetype 2)
    ;;※以前ここにあった d の計算は未使用だったため削除

    (setq ls_p
          (if bool
              (mapcar
               '(lambda(lst ls_i)
                  (mapcar '(lambda(i)(nth i lst))ls_i))
               (cal_twisttangent;;cal_radiustwist;;
                radius_arcmove p
                p_line00 p_line01 p_line10 p_line11 vec_line0 vec_line1 length_s)
               (list(list 0 1 2 3 4 5)(list 0 2 1 3 4 5))
               )
            
            (mapcar
             '(lambda(lst ls_i)
                (mapcar '(lambda(i)(nth i lst))ls_i))
             (reverse
              
              ;; (cal_radiustwist
              ;;  radius_arcmove p
              ;;  p_line11 p_line10 p_line01 p_line00
              ;;  (mapcar '- vec_line1)(mapcar '- vec_line0)
              ;;  length_s)
              
              (cal_twisttangent
               radius_arcmove p
               p_line10 p_line11 p_line00 p_line01 vec_line1 vec_line0 length_s)
              )
             (list(list 0 1 2 3 4 5)(list 0 2 1 3 4 5))
             )
            )
          )

    (if ls_p
        (progn
          (setq bool_limit T)
          (set sym ls_p)
          )

      )
    
    )

   )
  
  )




(defun func_road_number(ls_in / vec p0 p1 ang ls_number str_number pp dd ww
                              vnam_line vnam_num0 vnam_num1 hand_line)
  (mapcar '(lambda(lst / sym str)(set(cdr lst)(cdr(assoc(car lst)ls_in))))
          (list(cons "NUMBER" 'str_number)
               (cons "POINT" 'pp)(cons "DIST" 'dd)(cons "WIDTH" 'ww)
               (cons "LINE" 'vnam_line)(cons "TEXT0" 'vnam_num0)(cons "TEXT1" 'vnam_num1)))

  (setq ls_number(mapcar '(lambda(a)(cdr(assoc "NUMBER" a)))ls_vnam_number))
  (if str_number T
    ((lambda( / ii)
       (setq ii 0)
       (while(vl-position(mix_strasc(list 27178 26029 "-"(itoa(setq ii(1+ ii)))))ls_number))
       (setq str_number(mix_strasc(list 27178 26029 "-"(itoa ii))))))
    )
  
  (if pp(setq dd(vlax-curve-getdistatpoint vnam_plane_road pp))
    (if(setq pp(vlax-curve-getpointatdist vnam_plane_road dd))T
      (setq pp((if(< dd 1e-8)vlax-curve-getstartpoint vlax-curve-getendpoint)
               vnam_plane_road))))
  (setq vec(xvla-normal vnam_plane_road pp)
        vec(if(= int_transdirection 0)(list(cadr vec)(-(car vec))0.)(list(-(cadr vec))(car vec)0.))
        p0(mapcar '(lambda(a b)(- a(* ww b))) pp vec)
        p1(mapcar '(lambda(a b)(+ a(* ww b))) pp vec)
        ang(angle p0 p1)
        p0(vlax-3d-point p0)p1(vlax-3d-point p1)
        )

  (if vnam_line
      (mapcar '(lambda(lst)((car lst)vnam_line(cadr lst)))
              (list(list vla-put-startpoint p0)(list vla-put-endpoint p1)))
    (progn
      (setq vnam_line
            (vla-addline
             (vla-get-modelspace(vla-get-activedocument(vlax-get-acad-object)))
             p0 p1)
            hand_line(vla-get-handle vnam_line) )
      
      (set_xda vnam_line(list(cons 1000 "ROADNUMBERTEMP")(cons 1000 "LINE")
                             (cons 1000 hand_line))"terraduct3d")
      (addkillobj vnam_line)
      )
    )
  
  (if vnam_num0 T
    (progn
      (setq vnam_num0
            (vla-addtext
             (vla-get-modelspace(vla-get-activedocument(vlax-get-acad-object)))
             "AAA"(vlax-3d-point 0. 0. 0.)0.25) )
      (set_xda vnam_num0(list(cons 1000 "ROADNUMBERTEMP")(cons 1000 "LINE")
                             (cons 1000 hand_line))"terraduct3d")
      
      (addkillobj vnam_num0)
      ))
  (vla-put-Alignment vnam_num0 13)
  (vla-put-rotation vnam_num0 ang)
  (vla-put-TextAlignmentPoint vnam_num0 p0)
  (vla-put-Textstring vnam_num0(mix_strasc(list str_number ":" 24038)))
  
  (if vnam_num1 T
    (progn
      (setq vnam_num1
            (vla-addtext
             (vla-get-modelspace(vla-get-activedocument(vlax-get-acad-object)))
             "AAA"(vlax-3d-point 0. 0. 0.)0.25))
      (set_xda vnam_num1(list(cons 1000 "ROADNUMBERTEMP")(cons 1000 "LINE")
                             (cons 1000 hand_line))"terraduct3d")
      (addkillobj vnam_num1)
      ))
  (vla-put-Alignment vnam_num1 13)
  (vla-put-rotation vnam_num1 ang)
  (vla-put-TextAlignmentPoint vnam_num1 p1)
  (vla-put-Textstring vnam_num1(mix_strasc(list str_number ":" 21491)))

  (list(cons "LINE" vnam_line)(cons "NUMBER" str_number)
       (cons "POINT" pp)(cons "DIST" dd)(cons "WIDTH" ww)
       (cons "TEXT0" vnam_num0)(cons "TEXT1" vnam_num1))
  )

(defun save_road_number( / lst ls_xdata)

  (if vnam_plane_road
      (progn

        (setq ls_xdata
              (mapcar '(lambda(lst / str dd ww)
                         (setq str(cdr(assoc "NUMBER" lst))
                               dd(cdr(assoc "DIST" lst))
                               ww(cdr(assoc "WIDTH" lst)))
                         (list(cons 1000 "NUMBER" )(cons 1000 str)
                              (cons 1000 "DIST" )(cons 1040 dd)
                              (cons 1000 "WIDTH")(cons 1040 ww)
                              )
                         )
                      ls_vnam_number)
              )
        (set_xda vnam_plane_road
                 (append(list(cons 1000 "PLANEROAD")
                             (cons 1000 "REVERSE")(cons 1071 int_transdirection)
                             )
                        (apply 'append ls_xdata))
                 "terraduct3d")
        )
    )
  
  )




;;bool_loop はメインのコマンドループ(axd_command_loop)が使っている変数と同名なので
;;必ずローカルにする。グローバルのまま nil で終わるとループが黙って終了する
(defun load_las_to_grid(str_lasxml / bool_loop size_file int_time ms_loop ms_max
                                     ms_start str_data str_path str_laspath )
  ;; (setq cpath_terraduct3d(strcat (getenv "APPDATA")"\\" "terraduct3d-ac" "\\app"))
  (setq str_data(strcat cpath_terraduct3d "\\pyexe\\grid_points.csv")
        str_path(strcat cpath_terraduct3d "\\pyexe\\main.exe")
        bool_loop T size_file nil
        int_time 100 ms_loop nil ms_max 20000
        size_grid 0.5
        )

  (setq str_laspath(getfiled(strcat "Select " str_lasxml " file")(getvar "DWGPREFIX")str_lasxml 0))
  (if(null str_laspath)
      (alert(mix_strasc(list 12501 12449 12452 12523 12364 36984 25246 12373 12428 12414 12379 12435 12391 12375 12383)))
    
    (progn
      (setq str_lasfile str_laspath )
      
      (while(setq num(vl-string-search "\\" str_lasfile))
        (setq str_lasfile(substr str_lasfile(+ num 2))))
      
      (if(findfile str_data)(vl-file-delete str_data))
      ;; (startapp str_path "")
      
      (setq wsh (vlax-create-object "WScript.Shell"))
      (setq cmd(strcat "\"" str_path "\" "
                       "\"" str_lasxml  "\" "
                       "\"" str_laspath "\""))
      (vlax-invoke-method wsh 'Run cmd 0 :vlax-true)
      (vlax-release-object wsh)

      (setq ms_loop(getvar "MILLISECS"))
      (while bool_loop
        (setq ms_start(getvar "MILLISECS"))
        (if(>(- ms_start ms_loop)ms_max)(setq bool_loop nil))
        (while(<(-(getvar "MILLISECS")ms_start)int_time) )
        (if(findfile str_data)
            (if(= size_file(vl-file-size str_data))(setq bool_loop nil)
              (setq size_file(vl-file-size str_data)) ))
        )


      (if(null(findfile str_data))
          (progn
            (setq dict_name nil)
            (alert(mix_strasc(list 35501 12415 36796 12415 12395 22833 25943 12375 12414 12375 12383)))
            )
        (progn
          ;;(vla-startUndoMark (vla-get-ActiveDocument (vlax-get-Acad-Object)))
          ;; (setq *error*
          ;;       (lambda(msg)
          ;;         (if(= msg "")T
          ;;           (vla-EndUndoMark (vla-get-ActiveDocument (vlax-get-Acad-Object))) )
          ;;         (mapcar '(lambda(a / v)
          ;;                    (if a(if(if(=(type a)'ENAME)
          ;;                                (if(entget a)(setq v(vlax-ename->vla-object a))(progn nil))
          ;;                              (if(setq v a a(vlax-vla-object->ename a))(entget a)(progn nil)) )
          ;;                             (vla-delete v))))
          ;;                 ls_vnam_killobj)
          ;;         (setq ls_vnam_killobj nil vnam_guide nil)
          ;;         (if (= 'FILE (type file_r)) (close file_r))
          ;;         (gc)
          ;;         (setq *error*(lambda(msg)(princ msg)))
          ;;         (princ msg)
          ;;         )
          ;;       ls_vnam_killobj nil
          ;;       )
          
          
          (setq num_limit 100000 num_start 0 num_last nil num_elem 1000 str_grid "1"
                delta_grid(atof str_grid))
          
          (setq spantime0(getvar "MILLISECS")
                ls_grid(list)
                file_r (open str_data "r")
                )

          
          (if(= int_inputlasinsert 0)T
            (progn
              (setq str_bname(strcat "input-lasgrid-" str_lasfile ))
              (if(vl-catch-all-error-p
                  (setq block(vl-catch-all-apply 'vla-Item(list vnam_blocktable str_bname))))
                  (setq block(vla-Add vnam_blockTable(vlax-3d-point 0 0 0)str_bname) )
                (progn
                  (if(setq set_ent(ssget "X"(list(cons 2 str_bname))))
                      (progn
                        (setq num(sslength set_ent))
                        (while(>(setq num(1- num))-1)
                          (setq vnam(vlax-ename->vla-object(ssname set_ent num)))
                          (vla-delete vnam)
                          )
                        ))
                  (vla-delete block)
                  (mapcar '(lambda(v)
                             (vlax-release-object v)
                             (setq ls_vla-release(vl-remove v ls_vla-release))
                             )
                          (list block))
                  (setq block(vla-Add vnam_blockTable(vlax-3d-point 0 0 0)str_bname))
                  )
                )
              (setq ls_vla-release(cons block ls_vla-release) )
              ))

          (setq z_ave 0. z_min nil z_max nil)
          (while(setq str(read-line file_r))
            (setq x(atof str)str(substr str(+(vl-string-search "," str)2))
                  y(atof str)str(substr str(+(vl-string-search "," str)2))
                  z(atof str)z_ave(+ z_ave z)
                  )
            (if z_min(setq z_min(min z z_min)z_max(max z z_max))
              (setq z_min z z_max z))

            (if(= int_inputlasinsert 0)T(vla-addpoint block(vlax-3d-point x y z)))
            
            (setq nx(/ x size_grid) nx(floor_int nx)
                  ny(/ y size_grid) ny(floor_int ny)
                  
                  ls_grid(cons(list(strcat(itoa nx)"$"(itoa ny))z)ls_grid)
                  )
            )
          (close file_r)

          
          (if(= int_inputlasinsert 0)T
            (mapcar '(lambda(v)
                       (vlax-release-object v)
                       (setq ls_vla-release(vl-remove v ls_vla-release))
                       )
                    (list block))
            )
          
          (if(= int_inputlasinsert 1)
              (vla-InsertBlock
               (vla-get-ModelSpace(vla-get-ActiveDocument(vlax-get-acad-object)))
               (vlax-3d-point 0 0 0)str_bname 1 1 1 0)
            )
          

          ;; (setq dicts_all(vla-get-Dictionaries(vla-get-ActiveDocument (vlax-get-acad-object)))
          ;;       vnam(vlax-ename->vla-object entna)
          ;;       vec_insert(vlax-safearray->list(vlax-variant-value(vla-get-normal vnam)))
          ;;       p_insert(vlax-safearray->list(vlax-variant-value(vla-get-insertionpoint vnam)))
          ;;       str_nameblock(vla-get-name vnam)
          ;;       )
          
          ;; (while(vl-string-search "*" str_nameblock)
          ;;   (setq str_nameblock(vl-string-subst "^^^^" "*" str_nameblock))
          ;;   )
          ;; (if spantime0 T(setq spantime0(getvar "MILLISECS")))

          ;; (defun dict_las_input(str_lasfile bool)

          (setq ls_xdata(list))
          (setq dict_name(strcat "lasgrid" "-" str_lasfile ))
          ;; (setq dict_grid(vl-catch-all-apply 'vla-Item (list dicts_all(strcat dict_name))))
          (if(if nil(assoc dict_name ls_lasgrid);;あれば作る必要がない
               (progn ;;あったら消して作る
                 (if(setq dict_grid(cdr(assoc dict_name ls_lasgrid)))(vla-delete dict_grid))
                 nil
                 ) )
              (progn  nil ) ;;すでにあるものを使うとき 通ることはない
            (progn ;;新しく作るとき
              
              (setq z_ave(/ z_ave(length ls_grid)))
              (setq dict_grid(vla-Add dicts_all dict_name))
              (setq xrec(vla-AddXRecord dict_grid "GRID-SIZE_CENTER"))
              (setq array_data(vlax-make-safearray vlax-vbVariant(cons 0 3))
                    array_type(vlax-make-safearray vlax-vbInteger(cons 0 3)))
              (vlax-safearray-fill array_type(list 1040 1040 1040 1040))
              (vlax-safearray-fill array_data(list size_grid z_ave z_min z_max))
              (vla-SetXRecordData xrec array_type array_data )

              (setq array_data(vlax-make-safearray vlax-vbVariant(cons 0 0))
                    array_type(vlax-make-safearray vlax-vbInteger(cons 0 0)))
              (vlax-safearray-fill array_type (list 1040))
              (mapcar
               '(lambda(lst)
                  (setq xrec(vla-AddXRecord dict_grid(strcat(car lst))))
                  (vlax-safearray-fill array_data(cdr lst))
                  (vla-SetXRecordData xrec array_type array_data )
                  )
               ls_grid)
              
              (if(setq lst(assoc dict_name ls_lasgrid))(vl-remove lst ls_lasgrid))
              (setq ls_lasgrid(cons(cons dict_name dict_grid)ls_lasgrid))
              )
            )
          
          ;;(vla-startUndoMark (vla-get-ActiveDocument (vlax-get-Acad-Object)))
          ;; (princ "\nFinish")

          (alert(mix_strasc(list 35501 36796 23436 20102)))
          ))
      ))
  
  ;; (*error* "")
  dict_name
  )

(defun depth_level_str(pg p0 / z)
  (setq z(caddr p0))
  (strcat "GL"(if(<(- z(caddr pg))0)"-" "+")"<>\\P"
          "EL = "(rtos z 2 int_unitelevation))
  )

(defun cal_arcposition
    (rr ph pc px vec0 vecn0 vec1 vecn1 / dd dx pco pho pcc vecc)
  ;;phかpcはどちらかだけでもよい
  (setq dd(apply '+(mapcar '*(if ph ph pc)vec0))
        dx(apply '+(mapcar '* px vec0))
        )
  
  
  (cond
   ((> dd(+ dx rr))
    (if ph T(setq ph(mapcar '(lambda(a b)(+ a(* rr b)))pc vecn0)))
    (if pc T(setq pc(mapcar '(lambda(a b)(+ a(* -1 rr b)))ph vecn0)))
    (setq dd(apply '+(mapcar '*(mapcar '- pc px)vecn1))
          pco(mapcar '(lambda(a b)(+ a(*(+ rr(- dd))b)))pc vecn1)
          dd(-(* 4(expt rr 2))(expt(+ rr(- dd))2))
          )
    (if(< dd 0)(progn(alert "arcerror" )nil)
      (progn
        (setq dd(sqrt dd)
              pco(mapcar '(lambda(a b)(+ a(* dd b)))pco vec1)
              pho(mapcar '(lambda(a b)(+ a(* -1 rr b)))pco vecn1)
              pcc(mapcar '(lambda(a b)(* 0.5(+ a b)))pc pco)
              )
        (list pc ph pco pho pcc)
        ))
    )

   ((< dd dx )
    (if ph T(setq ph(mapcar '(lambda(a b)(+ a(* -1 rr b)))pc vecn0)))
    (if pc T(setq pc(mapcar '(lambda(a b)(+ a(* rr b)))ph vecn0)))
    (setq dd(apply '+(mapcar '*(mapcar '- pc px)vecn1))
          pco(mapcar '(lambda(a b)(+ a(* -1(+ rr dd)b)))pc vecn1)
          dd(-(* 4(expt rr 2))(expt(+ rr dd)2))
          )
    
    
    (if(< dd 0)(progn(alert "arcerror01" )nil)
      (progn
        (setq dd(sqrt dd)
              pco(mapcar '(lambda(a b)(+ a(* dd b)))pco vec1)
              pho(mapcar '(lambda(a b)(+ a(* rr b)))pco vecn1)
              pcc(mapcar '(lambda(a b)(* 0.5(+ a b)))pc pco)
              )
        (list pc ph pco pho pcc)
        ))
    )
   (T
    (setq vecc(unit_vector(mapcar '+ vec0 vec1))
          dd(/ rr(apply '+(mapcar '* vecn0 vecc)))
          pc(mapcar '(lambda(a b)(+ a(* dd b)))px vecc)
          )
    (list pc(mapcar '(lambda(a b)(+ a(* -1 rr b)))pc vecn0)
          nil nil(mapcar '(lambda(a b)(+ a(* -1 rr b)))pc vecn1))
    )
   )
  )

(defun c:test_cal_radiustwist()
  (setq p00(getpoint) p01(getpoint)
        p10(getpoint) p11(getpoint)
        p_tan p01
        vec0(unit_vector(mapcar '- p01 p00))
        vec1(unit_vector(mapcar '- p11 p10))
        rr 5.
        )


  
  (mapcar '(lambda(lst / pc p0 p1 p2 v d)
             (mapcar 'set '(pc p0 p1 p2 v)lst)
             (setq d(apply '+(mapcar '* v pc)))
             (make_arcdimension
              nil(list pc p0 p1 p2 rr v d " " (getvar "DIMSTYLE") ))
             )
          (cal_radiustwist rr p_tan p00 p01 p10 p11 vec0 vec1 0))
  (princ)
  )

(defun cal_fixedstuff
    (rr p_tan p00 p01 p10 p11 vec0 vec1 length_straight
        / length_arc_min length_arc_max length_arc_x vec_p
        variable_a variable_b variable_c variable_d vec_tan
        dist_diff num_limit bool_loop ls_out radius1 radius2 delta
        bool_loop_r  p_tan1 delta_r px hx vec_normal rr_min)

  (setq length_fix 1.
        angle_fix(/ length_fix rr)
        num_max(1+(fix(/(* 1. pi)angle_fix)))
        vecz(unit_vector(cross_product vec0 vec1))
        vecx(trans-x vec0(list 0 0 1)vecz)
        vecy(cross_product vecx vecz)
        vec_p(mapcar '- p10 p00)
        delta_h(apply '+(mapcar '* vec_p vecz))
        vec1t(list(apply '+(mapcar '* vecx vec1))
                  (apply '+(mapcar '* vecy vec1))
                  0)
        vec1t(unit_vector vec1t)
        ;; p10t(list(apply '+(mapcar '* vecx p10))
        ;;          (apply '+(mapcar '* vecy p10))
        ;;          (apply '+(mapcar '* vecz p10)))
        ;; p11t(list(apply '+(mapcar '* vecx p11))
        ;;          (apply '+(mapcar '* vecy p11))
        ;;          (apply '+(mapcar '* vecz p11)))
        
        vec_plane1(list(-(cadr vec1t))(car vec1t)0)
        sin_angplane(abs(cadr vec1t))
        cos_angplane(-(car vec1t))

        
        ;; dist_crossplane(/(apply '+(mapcar '*(mapcar '- p
        
        num0 0
        ls_fix(list)
        )
  
  (while(<(setq num0(1+ num0))num_max)
    (setq angle_cone(* 0.5 num0 angle_fix)
          length_tan0(/(* rr(sin angle_cone))(cos angle_cone))
          ;;angle_cone(-(* 2.0 pi)angle_tan0)
          num1 -1)
    (while(<(setq num1(1+ num1))num_max)
      (setq angle_tan1(* 0.5 num1 angle_fix)
            length_tan1(/(* rr(sin angle_tan1))(cos angle_tan1))
            length_tan(+ length_tan0 length_tan1)

            )
      
      
      
      
      )
    )
  
  (setq vec_normal(cross_product vec1 vec_p)
        vec_normal(unit_vector(cross_product vec_normal vec1))
        hx(apply '+(mapcar '* vec_normal vec_p))
        p_tan1(mapcar '(lambda(a b)(+ a(* hx b)))p01 vec_normal)
        
        )

  
  
  (while bool_loop_r
    (setq length_arc_min (* rr 0.1) 
          vec_p(mapcar '- p_tan1 p01)
          length_arc_max(distance p01 p_tan1)
          variable_a(expt length_arc_max 2)
          variable_b(* 2.(apply '+(mapcar '* vec_p vec0)))
          variable_c(* 2.(apply '+(mapcar '* vec_p vec1)))
          variable_d(* 2.(1+(apply '+(mapcar '* vec0 vec1))))
          num_limit 100 bool_loop T
          delta(* rr 0.1)
          )
    
    (while bool_loop
      (setq length_arc_x
            (/(+ variable_a(* length_arc_min variable_b))
              (+ variable_c(* length_arc_min variable_d)))
            vec_tan
            (mapcar '(lambda(a b c)
                       (+ a(*  length_arc_min b)(* -1. length_arc_x c)))
                    vec_p vec0 vec1)
            vec_tan(unit_vector vec_tan)
            radius1(apply '+(mapcar '* vec0 vec_tan))
            radius2(apply '+(mapcar '* vec1 vec_tan))
            )
      
      (if(<(abs(1+ radius1))1e-8)
          (setq radius2(* length_arc_x(sqrt(/(+ 1 radius2)(- 1 radius2))))
                radius1 radius2 dist_diff 0 )
        (if(<(abs(1- radius2))1e-8)
            (setq radius1(* length_arc_min(sqrt(/(- 1 radius1)(+ 1 radius1))))
                  radius2 radius1 dist_diff 0 )
          (setq radius1(* length_arc_min(sqrt(/(- 1 radius1)(+ 1 radius1))))
                radius2(* length_arc_x(sqrt(/(+ 1 radius2)(- 1 radius2))))
                dist_diff(- radius2 radius1) )
          ))

      (setq num_limit(1- num_limit))
      (cond
       ((< num_limit 0)(setq bool_loop nil))
       ((<(abs radius1)1e-8)(setq length_arc_min(+ length_arc_min delta)))
       ((<(abs dist_diff)1e-8)
        (setq bool_loop nil)
        
        
        (setq dist_diff(- rr radius1))
        (cond
         ((if(null rr_min)(>(setq rr_min radius1)rr))
          (setq bool_loop_r nil)
          )
         ((<(abs dist_diff)1e-6)
          (setq vech0(unit_vector(cross_product vec_tan vec0))
                vech1(unit_vector(cross_product vec_tan vec1))
                
                pt00 p01
                pc0 (mapcar '(lambda(a b)(+ a(* rr b)))pt00(cross_product vech0 vec0))
                pt01(mapcar '(lambda(a b)(+ a(* rr b)))pc0(cross_product vec_tan vech0))
                pt02(mapcar '(lambda(a b)(+ a(* rr b)))
                            pc0(unit_vector(mapcar '(lambda(a b c)(+ a b(* -2 c)))pt00 pt01 pc0)))

                pt10 p_tan1
                pc1 (mapcar '(lambda(a b)(+ a(* rr b)))pt10(cross_product vech1 vec1))
                pt11(mapcar '(lambda(a b)(+ a(* rr b)))pc1(cross_product vec_tan vech1))
                pt12(mapcar '(lambda(a b)(+ a(* rr b)))
                            pc1(unit_vector(mapcar '(lambda(a b c)(+ a b(* -2 c)))pt10 pt11 pc1)))
                ls_out(list(list pc0 pt00 pt01 pt02 vech0 length_straight)
                           (list pc1 pt10 pt11 pt12 vech1 length_straight))
                )
          )
         ((< rr radius1)
          (if(< delta_r 0)(setq delta_r(* -0.1 delta_r)))
          (setq p_tan1(mapcar '(lambda(a b)(+ a(* delta_r b)))p_tan1 vec1))
          )
         (T
          (if(> delta_r 0)(setq delta_r(* -0.1 delta_r)))
          (setq p_tan1(mapcar '(lambda(a b)(+ a(* delta_r b)))p_tan1 vec1))
          )
         
         )
        )
       
       ((< dist_diff 0.)
        (if(< delta 0)(setq delta(* -0.1 delta)))
        (setq length_arc_min(+ length_arc_min delta))
        )
       ;; ((< radius1 rr)
       ;;  (setq bool_loop nil))
       (T
        (if(> delta 0)(setq delta(* -0.1 delta)))
        (setq length_arc_min(+ length_arc_min delta)))
       )
      )
    
    )
  ls_out
  )


(defun cal_radiustwist
    (rr p_tan p00 p01 p10 p11 vec0 vec1 length_straight
        / length_arc_min length_arc_max length_arc_x vec_p
        variable_a variable_b variable_c variable_d vec_tan
        dist_diff num_limit bool_loop ls_out radius1 radius2 delta
        bool_loop_r  p_tan1 delta_r px hx vec_normal rr_min)

  (setq bool_loop_r T delta_r(* rr 0.1))
  (setq vec_p(mapcar '- p11 p01)
        vec_normal(cross_product vec1 vec_p)
        vec_normal(unit_vector(cross_product vec_normal vec1))
        hx(apply '+(mapcar '* vec_normal vec_p))
        p_tan1(mapcar '(lambda(a b)(+ a(* hx b)))p01 vec_normal)
        
        )
  
  
  (while bool_loop_r
    (setq length_arc_min (* rr 0.1) 
          vec_p(mapcar '- p_tan1 p01)
          length_arc_max(distance p01 p_tan1)
          variable_a(expt length_arc_max 2)
          variable_b(* 2.(apply '+(mapcar '* vec_p vec0)))
          variable_c(* 2.(apply '+(mapcar '* vec_p vec1)))
          variable_d(* 2.(1+(apply '+(mapcar '* vec0 vec1))))
          num_limit 100 bool_loop T
          delta(* rr 0.1)
          )
    
    (while bool_loop
      (setq length_arc_x
            (/(+ variable_a(* length_arc_min variable_b))
              (+ variable_c(* length_arc_min variable_d)))
            vec_tan
            (mapcar '(lambda(a b c)
                       (+ a(*  length_arc_min b)(* -1. length_arc_x c)))
                    vec_p vec0 vec1)
            vec_tan(unit_vector vec_tan)
            radius1(apply '+(mapcar '* vec0 vec_tan))
            radius2(apply '+(mapcar '* vec1 vec_tan))
            )
      
      (if(<(abs(1+ radius1))1e-8)
          (setq radius2(* length_arc_x(sqrt(/(+ 1 radius2)(- 1 radius2))))
                radius1 radius2 dist_diff 0 )
        (if(<(abs(1- radius2))1e-8)
            (setq radius1(* length_arc_min(sqrt(/(- 1 radius1)(+ 1 radius1))))
                  radius2 radius1 dist_diff 0 )
          (setq radius1(* length_arc_min(sqrt(/(- 1 radius1)(+ 1 radius1))))
                radius2(* length_arc_x(sqrt(/(+ 1 radius2)(- 1 radius2))))
                dist_diff(- radius2 radius1) )
          ))

      (setq num_limit(1- num_limit))
      (cond
       ((< num_limit 0)(setq bool_loop nil))
       ((<(abs radius1)1e-8)(setq length_arc_min(+ length_arc_min delta)))
       ((<(abs dist_diff)1e-8)
        (setq bool_loop nil)
        
        
        (setq dist_diff(- rr radius1))
        (cond
         ((if(null rr_min)(>(setq rr_min radius1)rr))
          (setq bool_loop_r nil)
          )
         ((<(abs dist_diff)1e-6)
          (setq vech0(unit_vector(cross_product vec_tan vec0))
                vech1(unit_vector(cross_product vec_tan vec1))
                
                pt00 p01
                pc0 (mapcar '(lambda(a b)(+ a(* rr b)))pt00(cross_product vech0 vec0))
                pt01(mapcar '(lambda(a b)(+ a(* rr b)))pc0(cross_product vec_tan vech0))
                pt02(mapcar '(lambda(a b)(+ a(* rr b)))
                            pc0(unit_vector(mapcar '(lambda(a b c)(+ a b(* -2 c)))pt00 pt01 pc0)))

                pt10 p_tan1
                pc1 (mapcar '(lambda(a b)(+ a(* rr b)))pt10(cross_product vech1 vec1))
                pt11(mapcar '(lambda(a b)(+ a(* rr b)))pc1(cross_product vec_tan vech1))
                pt12(mapcar '(lambda(a b)(+ a(* rr b)))
                            pc1(unit_vector(mapcar '(lambda(a b c)(+ a b(* -2 c)))pt10 pt11 pc1)))
                ls_out(list(list pc0 pt00 pt01 pt02 vech0 length_straight)
                           (list pc1 pt10 pt11 pt12 vech1 length_straight))
                )
          )
         ((< rr radius1)
          (if(< delta_r 0)(setq delta_r(* -0.1 delta_r)))
          (setq p_tan1(mapcar '(lambda(a b)(+ a(* delta_r b)))p_tan1 vec1))
          )
         (T
          (if(> delta_r 0)(setq delta_r(* -0.1 delta_r)))
          (setq p_tan1(mapcar '(lambda(a b)(+ a(* delta_r b)))p_tan1 vec1))
          )
         
         )
        )
       
       ((< dist_diff 0.)
        (if(< delta 0)(setq delta(* -0.1 delta)))
        (setq length_arc_min(+ length_arc_min delta))
        )
       ;; ((< radius1 rr)
       ;;  (setq bool_loop nil))
       (T
        (if(> delta 0)(setq delta(* -0.1 delta)))
        (setq length_arc_min(+ length_arc_min delta)))
       )
      )
    
    )
  ls_out
  )




(defun cal_twisttangent
    (rr p_tan p00 p01 p10 p11 vec0 vec1 length_straight /
        ls_out bool_loop bool_first dh0 dh1 ph0 ph1 vec_tan delta_dh
        cos0 cos1 sin0 sin1 dist_corner dist0 dist1
        pc0 pt00 pt01 pt02 pc1 pt10 pt11 pt12
        vech0 vech1 num_loop
        )

  (setq dh1(apply '+(mapcar '*(mapcar '- p_tan p11)vec1))
        ;;todo何のために計算していたの検証
        ;; dh0(apply '+(mapcar '*(mapcar '- p_tan p11)vec0))
        ;; dh0(/ dh0(apply '+(mapcar '* vec0 vec1)))
        ;; dh1(max dh1 dh0)
        delta_dh(* 0.1 rr)
        bool_loop T bool_first T
        dh1(- dh1 delta_dh)
        num_loop 2000;;準平行で収束しないとき無限ループになっていたため上限を設ける
        )


  (while bool_loop
    (if(<(setq num_loop(1- num_loop))0)(setq bool_loop nil))
    (setq dh1(+ dh1 delta_dh)
          ph1(mapcar '(lambda(a b)(+ a(* dh1 b)))p11 vec1)
          dist_corner(distance ph1 p_tan)
          vec_tan(mapcar '- ph1 p_tan)
          vec_tan(mapcar '(lambda(a)(/ a dist_corner))vec_tan)

          cos0(apply '+(mapcar '* vec0 vec_tan))
          sin0(sqrt(- 1.(expt cos0 2)))
          
          cos1(-(apply '+(mapcar '* vec1 vec_tan)))
          sin1(sqrt(- 1.(expt cos1 2)))
          )

    (if(or(<(abs sin0)1e-8)(<(abs sin1)1e-8))T
      (progn
        (setq dist0(/(* rr(+ 1. cos0))sin0)
              dist1(/(* rr(+ 1. cos1))sin1))
        (if bool_first
            (setq bool_first nil bool_loop(>=(+ dist0 dist1)dist_corner)))
        ))
    
    (cond
     (bool_first  )
     ((<(abs(- dist_corner dist0 dist1))1e-8)
      (setq vech0(unit_vector(cross_product vec_tan vec0))
            vech1(unit_vector(cross_product vec_tan vec1))
            pt00(mapcar '(lambda(a b)(+ a(* dist0 b)))p_tan vec0)
            pt01(mapcar '(lambda(a b)(+ a(* dist0 b)))p_tan vec_tan)
            dist0(+ dist0(* -1 rr(/ cos0 sin0)))
            pc0(mapcar '(lambda(a b c)(+ a(* dist0 b)(* dist0 c)))p_tan vec0 vec_tan)
            pt02(mapcar '(lambda(a b)(+ a(* rr b)))
                        pc0(unit_vector(mapcar '(lambda(a b c)(+ a b(* -2 c)))pt00 pt01 pc0)))

            pt10(mapcar '(lambda(a b)(+ a(* dist1 b)))ph1 vec1)
            pt11(mapcar '(lambda(a b)(+ a(* -1 dist1 b)))ph1 vec_tan)
            dist1(+ dist1(* -1 rr(/ cos1 sin1)))
            pc1(mapcar '(lambda(a b c)(+ a(* dist1 b)(* -1 dist1 c)))ph1 vec1 vec_tan)
            pt12(mapcar '(lambda(a b)(+ a(* rr b)))
                        pc1(unit_vector(mapcar '(lambda(a b c)(+ a b(* -2 c)))pt10 pt11 pc1)))

            ls_out(list(list pc0 pt00 pt01 pt02 vech0 length_straight)
                       (list pc1 pt10 pt11 pt12 vech1 length_straight)
                       )
            bool_loop nil
            )
      )
     ((>(* delta_dh(- dist_corner(+ dist0 dist1)))0)
      (setq delta_dh(* -0.1 delta_dh))
      )
     )

    )

  ls_out
  )


(defun connect_twist_curve
    (lst / p00 p01 p10 p11 r_bend length_straight str_alert
         vec0 vec1 vec2 vec3 cos_plane vec_plane sin_plane vec_plane height_plane 
         vec0n vec1n delta_ratio xx delta_x bool_loop pc
         vecp0 vecp1 length_slant cos_slant vec_normal sin_slant
         r_temp p1 p2 p3 vec_tan ls_p_through str_break bool_break)

  (setq str_break
        (mix_strasc(list 10 20870 24359 12398 20301 32622 12434
                         20219 24847 12395 35373 23450 12375 12390 12367 12384 12373 12356
                         )))
  ;;円弧の位置を任意に設定してください
  (if(setq bool_break(car lst))T(setq lst(cdr lst)))
  (mapcar 'set '(p00 p01 p10 p11 r_bend length_straight ls_p_through str_alert)lst)

  (cond
   ((progn
      (setq vec0(unit_vector(mapcar '- p00 p01))
            vec1(unit_vector(mapcar '- p11 p10))
            
            cos_plane(apply '+(mapcar '* vec0 vec1))
            vec_plane(cross_product vec0 vec1)
            sin_plane(distance(list 0 0 0)vec_plane)
            )
      (<(abs sin_plane)1e-8));;平行のとき
    (setq vec2(mapcar '- p10 p00)
          vec_normal(unit_vector(cross_product vec2 vec0)))
    

    (if(<(distance vec_normal(list 0 0 0))1e-8);;同一直線状
        (progn
          (princ;;同一直線状なので円弧を設定しません
           (mix_strasc(list "\n" str_alert "\n"
                            21516 19968 30452 32218 29366 12394 12398 12391 20870 24359 12434 35373 23450 12375 12414 12379 12435 )))
          
          (mapcar '(lambda(i)
                     (list(mapcar '+ p01(list r_bend 0 0))
                          p01 p01 p01(list 0 0 1)length_straight))
                  (list 0 1))
          )
      (if ls_p_through
          (mapcar '(lambda(lst / pc p0 p1 p2 vec)
                     (mapcar 'set '(pc p0 p1 p2)lst)
                     (list pc p0 p1 p2 vec_normal length_straight))
                  ls_p_through)
        (progn

          (setq vec3(cross_product vec0 vec_normal);;normalからみると必ず2本目が上
                d_space(* 0.5(apply '+(mapcar '* vec3 vec2))))
          
          (if(> d_space r_bend)
              (progn
                (x-alert;;2直線が平行で距離が開きすぎているため円弧を設定できません
                 (list str_alert "\n"
                       "2" 30452 32218 12364 24179 34892 12391 36317 38626 12364
                       38283 12365 12377 12366 12390 12356 12427 12383 12417
                       20870 24359 12434 35373 23450 12391 12365 12414 12379 12435
                       ))
                (list "BREAK")
                )
            (progn
              (if bool_break(princ str_break))
              (list "BREAK" vec_normal(apply '+(mapcar '* vec_normal p00))r_bend
                    p00 p01 p10 p11 vec0 vec1 length_straight
                    0(list vec3 d_space)
                    )
              ))
          )
        )
      )
    
    )
   ((progn
      (setq vec_plane(mapcar '(lambda(a)(/ a sin_plane))vec_plane)
            height_plane(apply '+(mapcar '*(mapcar '- p10 p00)vec_plane))
            )
      (<(abs height_plane)1e-8));;面内のとき

    
    (if(if ls_p_through
           (apply 'and
                  (mapcar
                   '(lambda(lst pd0 pd1 / pc p0 d)
                      (setq p0(cadr lst))
                      (if(<(distance(list 0 0 0)(cross_product(mapcar '- pd0 p0)(mapcar '- pd1 p0)))1e-6)T
                        (progn
                          (setq p0(caddr lst))
                          (<(distance(list 0 0 0)(cross_product(mapcar '- pd0 p0)(mapcar '- pd1 p0)))1e-6)
                          ))
                      )
                   ls_p_through(list p00 p10)(list p01 p11))))
        
        (mapcar '(lambda(lst / pc p0 p1 p2 vec)
                   (mapcar 'set '(pc p0 p1 p2)lst)
                   (list pc p0 p1 p2 vec_plane length_straight))
                ls_p_through)
      (progn
        (setq vec0n(cross_product vec_plane vec0)
              vec1n(cross_product vec1 vec_plane)
              pc(3dcross_3pl vec_plane(apply '+(mapcar '* vec_plane p00))
                             vec0n(+(apply '+(mapcar '* vec0n p00))r_bend)
                             vec1n(+(apply '+(mapcar '* vec1n p10))r_bend)
                             )
              p0(mapcar '(lambda(a b)(+ a(* -1 r_bend b)))pc vec0n)
              p1(mapcar '(lambda(a b)(+ a(* -1 r_bend b)))pc vec1n)
              p2(mapcar '(lambda(a b)(+ a(* -1 r_bend b)))
                        pc(unit_vector(mapcar '+ vec0n vec1n)))
              )
    
        (if bool_break(princ str_break))
        (list "BREAK" vec_plane(apply '+(mapcar '* vec_plane p00))r_bend
              p00 p01 p10 p11 vec0 vec1 length_straight
              1(list vec0n vec1n pc p0 p1 p2
                     (inters p0(mapcar '+ p0 vec0)p1(mapcar '+ p1 vec1)nil)
                     )
              )
        ))
    )
   (T


    
    (if(if ls_p_through
           (setq ls_p_through
                 (cal_twisttangent
                  r_bend
                  ((lambda(lst / pc p0 p1 p2 d x h)
                     (setq x(car lst))
                     (setq pc(car x)p0(cadr x)p1(caddr x))
                     (if(<(distance p0 p1)1e-8)
                         (setq x(cadr lst)pc(car x)p0(cadr x)p1(caddr x) ))
                     
                     (setq p2(mapcar '(lambda(a b)(* 0.5(+ a b)))p0 p1)
                           d(/(expt(distance pc p0)2)(distance pc p2))
                           p2(mapcar '(lambda(a b)(+ a(* d b)))
                                     pc(unit_vector(mapcar '(lambda(a b c)(+(* -2 a)b c))pc p0 p1)))
                           d(apply '+(mapcar '*(mapcar '- p2 p00)vec0))
                           p2(mapcar '(lambda(a b)(+ a(* d b)))p00 vec0)
                           )
                     p2
                     )
                   ls_p_through)
                  p00 p01 p10 p11 vec0 vec1 length_straight)))
        (mapcar '(lambda(lst bool)
                   (if bool lst(mapcar '(lambda(i)(nth i lst))(list 0 2 1 3 4 5))))
                ls_p_through(list T nil))
      (progn
        (if bool_break(princ str_break))
        (list "BREAK" nil nil r_bend
              p00 p01 p10 p11 vec0 vec1 length_straight
              2(list )
              )
        ))
    

    )
   )
  
  )



(defun c:preview_grid()
  (setq ii(getint((lambda(lst / ii)
                    (setq ii -1)
                    (strcat "["
                            (substr
                             (apply
                              'strcat
                              (mapcar '(lambda(a)(setq ii(1+ ii))(strcat "/"(itoa ii)" " a))lst)
                              )
                             2)
                            "]"))
                  (mapcar 'car ls_lasgrid)))
        dict(cdr(nth ii ls_lasgrid))
        )
  
  (if(vl-catch-all-error-p
      (setq xrec(vl-catch-all-apply 'vla-Item (list dict "GRID-SIZE_CENTER"))))
      (progn(alert "LASDATAERROR01")(quit)))
  (vla-GetXRecordData xrec 'array_type 'array_data )
  (setq lst(if array_data
               (mapcar 'vlax-variant-value
                       (vlax-safearray->list array_data)))
        )
  (mapcar 'set '(size_grid z_ave z_min z_max)lst)
  (vlax-for
   vnam dict
   (if(vl-catch-all-error-p
       (setq str(vl-catch-all-apply 'vla-get-name (list vnam))))
       T
     (if(= str "GRID-SIZE_CENTER")T
       (progn
         (setq nn(vl-string-search "$" str)
               nx(atoi(substr str 1 nn)) ny(atoi(substr str(+ nn 2)))
               x(*(+ nx 0.5)size_grid) y(*(+ ny 0.5)size_grid)
               )
         (vla-GetXRecordData vnam 'array_type 'array_data )
         (setq z(vlax-variant-value(car(vlax-safearray->list array_data))))
         (vla-addcircle
          (vla-get-modelspace(vla-get-activedocument(vlax-get-acad-object)))
          (vlax-3d-point x y z)0.1)
         
         ))
     )
   )
  
  (princ)
  )



;;グリッド番号 : a 以下の最大の整数(床関数)
;;  (fix a) は 0 方向へ切り捨てるので、負の値では 1 つ大きい番号になる。
;;  平面直角座標系では X も Y も負になるため、そのままだと
;;  原点をはさんでセルの区切りが半セルずれ、原点のセルだけ幅が 2 倍になる。
;;  ※LAS の取込(セルへの割り当て)と参照の両方でこれを使うこと。
;;    片方だけ直すと既存図面のグリッド辞書と番号が合わなくなる
(defun floor_int( a / n )
  (setq n(fix a))
  (if(and(< a 0.)(/=(float n)a))(1- n)n))

(defun cal_weight_grid
    (p dict size_grid int_width / x y z p00 p01 p10 p11 d
       int_deltax int_deltay nx0 ny0 nx1 ny1 ls_z ls_d ls_intx ls_inty ls_int
       str xrec array_type array_data ny nx ls_p z_ave sigma nn zz ww bool_just)
  (setq x(car p)y(cadr p)
        nx0(/ x size_grid)nx0(floor_int nx0)
        ny0(/ y size_grid)ny0(floor_int ny0)
        p00(list(*(+ nx0 0.5)size_grid)(*(+ ny0 0.5)size_grid))
        int_deltax(if(<=(car p00) x)1 -1)
        int_deltay(if(<=(cadr p00)y)1 -1)
        ;;nx1(+ nx0 int_deltax) ny1(+ ny0 int_deltay)
        )

  (if int_width T(setq int_width 1))
  
  ;; (setq p01(mapcar '+ p00(list(* int_deltax size_grid)0.)) 
  ;;       p10(mapcar '+ p00(list 0.(* int_deltay size_grid)))
  ;;       p11(mapcar '+ p10(list(* int_deltax size_grid)0.))
  ;;       )

  
  (setq ls_int(append(inclist(- int_width)0)(inclist 0(1+ int_width)))
        ls_inty ls_int
        ls_z(list))

  (while ls_inty
    (setq ny(+(*(car ls_inty)int_deltay)ny0) ls_inty(cdr ls_inty)
          ls_intx ls_int)
    (while ls_intx
      (setq nx(+(*(car ls_intx)int_deltax)nx0) ls_intx(cdr ls_intx))
      
      ;; (mapcar
      ;;  '(lambda(iy / str xrec array_type array_data ny nx)
      (setq str(strcat(itoa nx)"$"(itoa ny)))
      (if(vl-catch-all-error-p
          (setq xrec(vl-catch-all-apply 'vla-Item (list dict str))))
          nil
        (progn
          (vla-GetXRecordData xrec 'array_type 'array_data )
          (setq ls_z(cons(vlax-variant-value(car(vlax-safearray->list array_data)))
                         ls_z)
                ;;重み付けの基準はそのセルの中心。
                ;;  p00 に格子番号×セル寸法を足すと絶対座標を二重に足すことになり、
                ;;  平面直角座標系では距離が数十kmになって重みがどれも同じになる
                ;;  (＝距離による重み付けが効かず、単なる平均になっていた)
                ls_p(cons(list(*(+ nx 0.5)size_grid)(*(+ ny 0.5)size_grid))
                         ls_p)
                )
          ))
      )
    )
  
  (if(=(setq nn(length ls_z))0)nil
    (progn
      (setq z_ave(/(apply '+ ls_z)nn)
            sigma(sqrt(/(apply '+(mapcar '(lambda(z)(expt(- z z_ave)2))ls_z))nn))
            ww 0 zz 0 bool_just nil)
      (mapcar
       '(lambda(z pg)
          (if bool_just T
            (if(>(abs(- z z_ave))(* 2 sigma))T
              ;;p は 3D で渡されることがあるので平面距離で測る
              (if(setq bool_just(<(setq d(distance(carxy p)pg))1e-8))
                  (setq zz z ww 1.)
                (setq d(/ 1. d)zz(+ zz(* z d))ww(+ ww d))
                )))
          )
       ls_z ls_p)
      ;;2σ で全部はじかれると 0 除算になるので、そのときは単純平均にする
      (list x y(if(< ww 1e-12)z_ave(/ zz ww)))
      ))
  
  ;; (setq ls_d(mapcar '(lambda(z pg)(if z(distance p pg)0.))ls_z(list p11 p10 p01 p00))
  ;;       ww(apply '+ ls_d)
  ;;       )
  ;; (if(= ww 0.)nil
  ;;   (list x y(/(apply '+(mapcar '(lambda(a b)(if b(* a b)0.))ls_d ls_z))ww))
  ;;   )
  )


(defun project_to_ground ;;外れ値の検証方法を考える
    (ls_p vec_proj lst
          / str_las height_ground cosdist dict xrec num_limit delta_proj
          ls_gridlevel d v n bool ls_out bool_verti
          )
  
  (if(setq str_las(car lst))
      T
    (if(setq height_ground(cadr lst))
        T
      (setq height_ground 0.)))
  
  (setq cosdist(caddr vec_proj) num_limit 1000
        bool_verti(<(distance(list 0 0)(carxy vec_proj))1e-8))

  (cond
   ;;bool_verti の綴り誤り(vec_verti)で、この分岐は一度も成立していなかった
   ((if bool_verti(<(abs cosdist)1e-8))
    nil)


   ((<(abs cosdist)1e-8);;地表面への投影方向がビュー方向に対し直角であるため地表面に投影することはできません
    (princ(mix_strasc(list "\n" 22320 34920 38754 12408 12398 25237 24433 26041 21521 12364 12499 12517 12540 26041 21521 12395 23550 12375 30452 35282 12391 12354 12427 12383 12417 22320 34920 38754 12395 25237 24433 12377 12427 12371 12392 12399 12391 12365 12414 12379 12435 )))
    ;;ビューの方向を修正してEnter
    ;; (getint(mix_strasc(list "\n" 12499 12517 12540 12398 26041 21521 12434 20462 27491 12375 12390 "Enter" )))
    ;; (cal_viewtopleft textsize_guide_bo_temp x_guidebase y_guidebase_temp 10. T )
    
    nil)
   (height_ground
    (mapcar
     '(lambda(p / d)
        (setq d(/(- height_ground(caddr p))cosdist))
        (mapcar '(lambda(a b)(+ a(* d b)))p vec_proj)
        )
     ls_p)
    )
   
   ((setq dict(cdr(assoc str_las ls_lasgrid)))
    (if(vl-catch-all-error-p
        (setq xrec(vl-catch-all-apply 'vla-Item (list dict "GRID-SIZE_CENTER"))))
        (progn(alert "LASDATAERROR01")(quit)))
    (vla-GetXRecordData xrec 'array_type 'array_data )
    (setq lst(if array_data
                 (mapcar 'vlax-variant-value
                         (vlax-safearray->list array_data)))
          )
    (mapcar 'set '(size_grid z_ave z_min z_max)lst)

    (if(<(setq sindist(sqrt(- 1.(expt cosdist 2))))1e-8)T
      (setq delta_proj(/ size_grid sindist)))
    
    (if(<(caddr vec_proj)0)((lambda(a b)(setq p_min b p_max a))p_min p_max))
    
    (mapcar
     '(lambda(p / num z zz nx0 ny0 nx1 ny1 bool p_end p_min p_max p_plane0 p_plane1 ang_plane
                bool_yx nx ny p p_pre p0 p1 deltaz pb0 pb1)
        
        (setq d(/(- z_min(caddr p))cosdist)
              p_min(mapcar '(lambda(a b)(+ a(* d b)))p vec_proj)
              d(/(- z_max(caddr p))cosdist)
              p_max(mapcar '(lambda(a b)(+ a(* d b)))p vec_proj)
              p_plane0(carxy p_min)p_plane1(carxy p_max)
              ang_plane(angle p_plane0 p_plane1)
             
              nx0(/(car p_plane0)size_grid) nx0(floor_int nx0)
              ny0(/(cadr p_plane0)size_grid)ny0(floor_int ny0)
              nx1(/(car p_plane1)size_grid) nx1(floor_int nx1)
              ny1(/(cadr p_plane1)size_grid)ny1(floor_int ny1)
              
              )

        
        (if(and(= nx0 nx1)(= ny0 ny1))
            (progn
              ;;int_width=3 → 7×7=49セル(0.5mグリッドなら 3.5m 四方)を逆距離加重する。
              ;;以前は 2(5×5=25セル)だったが、3 のほうが結果が良いので替えてある
              (cal_weight_grid p_plane0 dict size_grid 3)
              
              
              )
          (progn
            (setq d(distance p_min p_max)
                  n(1+(fix(/ d delta_proj)))
                  d(/ d n) v(mapcar '(lambda(a)(* d a))vec_proj)
                  n(1+ n)
                  p(mapcar '- p_min v)
                  bool T int_pm nil)
            
            ;;前後で正負逆転するところを見つける
            (while(and bool(>(setq n(1- n))-1))
              (setq p(mapcar '+ p v)
                    nx(/(car p)size_grid) nx(floor_int nx)
                    ny(/(cadr p)size_grid)ny(floor_int ny))

              ;; (vla-addcircle
              ;;  (vla-get-modelspace(vla-get-activedocument(vlax-get-acad-object)))
              ;;  (vlax-3d-point p)0.01)

              
              (if(setq z((lambda(str / xrec array_type array_data)
                           (if(vl-catch-all-error-p
                               (setq xrec(vl-catch-all-apply 'vla-Item (list dict str))))
                               nil
                             (progn
                               (vla-GetXRecordData xrec 'array_type 'array_data )
                               (vlax-variant-value(car(vlax-safearray->list array_data)))
                               ))
                           )
                         (strcat(itoa nx)"$"(itoa ny)))
                       )
                  (progn
                    (setq deltaz(- z(caddr p)))
                    (if(if int_pm(<(* int_pm deltaz)0))
                        (setq bool nil pb1 p)
                      (setq int_pm(if(> deltaz 0)1 -1)
                            pb0 p))
                    ))
              )
            
            (if bool nil
              (progn
                (setq p0(cal_weight_grid pb0 dict size_grid nil)
                      p1(cal_weight_grid pb1 dict size_grid nil)
                      )

                ;; (vla-addline
                ;;  (vla-get-modelspace(vla-get-activedocument(vlax-get-acad-object)))
                ;;  (vlax-3d-point p0)(vlax-3d-point p1))
                ;; (vla-addline
                ;;  (vla-get-modelspace(vla-get-activedocument(vlax-get-acad-object)))
                ;;  (vlax-3d-point pb0)(vlax-3d-point pb1))

                
                (inters p0 p1 pb0 pb1);;nilつけない
                ))
            )
          )
        )
     ls_p)
    )
   (T;;投影対象がありません
    ;;点ごとに呼ばれるので、同じ地表面データについては 1 回だけ知らせる。
    ;;  (図面を開き直して ls_lasgrid が作り直されていないときなどに、
    ;;   ダイアログが点の数だけ出て操作できなくなっていた)
    (if(= str_warned_lasground(if str_las str_las ""))T
      (progn
        (setq str_warned_lasground(if str_las str_las ""))
        (x-alert(list 25237 24433 23550 35937 12364 12354 12426 12414 12379 12435))))
    nil
    )
   
   )
  
  )


(defun get-polyface-data (ename / e data verts faces int_type)
  (setq e (entnext ename))
  (while e
    (setq data (entget e)int_type(cdr (assoc 70 data))
          e(if (= "SEQEND" (cdr (assoc 0 data)))nil(entnext e)) )
    (cond
     ((= int_type 192) ;; 頂点
      (setq verts (cons(cdr (assoc 10 data))verts))
      )
     ((= int_type 128) ;; フェース
      (setq faces(cons(mapcar '(lambda(i)(1-(abs(cdr(assoc i data)))))
                              (list 71 72 73 74))faces) )
      )
     )
    )
  (setq verts(reverse verts))
  (mapcar '(lambda(lst)(mapcar '(lambda(i j)(nth i verts))lst(list 1 2 3)))
          faces)
  )


(princ)
